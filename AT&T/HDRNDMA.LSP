;hdrndma
;
;--------* Stone & Webster Enginerring Corp
;--------* CAD/CAE
;--------* Mechanical Application
;--------* 031296                       jdc
;
;--------* This file contains the code used to draw round duct
;--------* fittings
;
;--------* 30 Deg Elbow (Side) Short Radius
;
(defun c:REL30S ()
(inpnt)
(command "pline" (list (+ ptx (* #DIA -0.2990381056))
                       (+ pty (* #DIA 0.4820508075)))
"W" 0.00 0.00 (list (+ ptx (* #DIA 0.5669872981))
                    (+ pty (* #DIA -0.0179491924)))
"A" "A" 30.00 (list (+ ptx (* #DIA 0.50)) (+ pty (* #DIA -0.2679491924)))
"L" (list (+ ptx (* #DIA -0.50)) (+ pty (* #DIA -0.2679491924)))
"A" "A" -30.00 (list (+ ptx (* #DIA -0.2990381056))
                     (+ pty (* #DIA 0.4820508075)))
"L" "cl" nil)
       (ROTZ)
       (reset nil)
       (princ)
 )
;
;--------* 30 Deg Elbow (Side) Long Radius
;
(defun c:REL30L ()
(inpnt)
(command "pline" (list (+ ptx (* #DIA -0.2320508075))
                       (+ pty (* #DIA 0.5980762113)))
"W" 0.00 0.00 (list (+ ptx (* #DIA 0.6339745962))
                    (+ pty (* #DIA 0.0980762113)))
"A" "A" 30.00 (list (+ ptx (* #DIA 0.50)) (+ pty (* #DIA -0.4019237886)))
"L" (list (+ ptx (* #DIA -0.50)) (+ pty (* #DIA -0.4019237886)))
"A" "A" -30.00 (list (+ ptx (* #DIA -0.2320508075))
                     (+ pty (* #DIA 0.5980762113)))
"L" "cl" nil)
       (ROTZ)
       (reset nil)
       (princ)
 )
;
;--------* 45 Deg Elbow (Side) Short Radius
;
(defun c:REL45S ()
(inpnt)
(command "pline" (list (+ ptx (* #DIA -0.0606601717))
                       (+ pty (* #DIA 0.6464466094)))
"W" 0.00 0.00 (list (+ ptx (* #DIA 0.6464466094))
                    (+ pty (* #DIA -0.0606601717)))
"A" "A" 45.00 (list (+ ptx (* #DIA 0.50)) (+ pty (* #DIA -0.4142135623)))
"L" (list (+ ptx (* #DIA -0.50)) (+ pty (* #DIA -0.4142135623)))
"A" "A" -45.00 (list (+ ptx (* #DIA -0.0606601717))
                     (+ pty (* #DIA 0.6464466094)))
"L" "cl" nil)
       (ROTZ)
       (reset nil)
       (princ)
 )
;
;--------* 45 Deg Elbow (Side) Long Radius
;
(defun c:REL45L ()
(inpnt)
(command "pline" (list (+ ptx (* #DIA 0.0857864376))
                       (+ pty (* #DIA 0.7928932188)))
"W" 0.00 0.00 (list (+ ptx (* #DIA 0.7928932188))
                    (+ pty (* #DIA 0.0857864376)))
"A" "A" 45.00 (list (+ ptx (* #DIA 0.50)) (+ pty (* #DIA -0.6213203435)))
"L" (list (+ ptx (* #DIA -0.50)) (+ pty (* #DIA -0.6213203435)))
"A" "A" -45.00 (list (+ ptx (* #DIA 0.0857864376))
                     (+ pty (* #DIA 0.7928932188)))
"L" "cl" nil)
       (ROTZ)
       (reset nil)
       (princ)
 )
;
;--------* 90 Deg Elbow (Side) Short Radius
;
(defun c:REL90S ()
(inpnt)
(command "pline" (list (+ ptx (* #DIA 1.00)) (+ pty (* #DIA 0.50)))
"W" 0.00 0.00 (list (+ ptx (* #DIA 1.00)) (+ pty (* #DIA -0.50)))
"A" "A" 90.00 (list (+ ptx (* #DIA 0.50)) (+ pty (* #DIA -1.00)))
"L" (list (+ ptx (* #DIA -0.50)) (+ pty (* #DIA -1.00)))
"A" "A" -90.00 (list (+ ptx (* #DIA 1.00)) (+ pty (* #DIA 0.50)))
"L" "cl" nil)
       (ROTZ)
       (reset nil)
       (princ)
 )
;
;--------* 90 Deg Elbow (Side) Long Radius
;
(defun c:REL90L ()
(inpnt)
(command "pline" (list (+ ptx (* #DIA 1.50)) (+ pty (* #DIA 0.50)))
"W" 0.00 0.00 (list (+ ptx (* #DIA 1.50)) (+ pty (* #DIA -0.50)))
"A" "A" 90.00 (list (+ ptx (* #DIA 0.50)) (+ pty (* #DIA -1.50)))
"L" (list (+ ptx (* #DIA -0.50)) (+ pty (* #DIA -1.50)))
"A" "A" -90.00 (list (+ ptx (* #DIA 1.50)) (+ pty (* #DIA 0.50)))
"L" "cl" nil)
       (ROTZ)
       (reset nil)
       (princ)
 )
;
;--------* Twin Bend (Side)
;
(defun c:RELTWN ()
(inpnt)
(command "pline" (list (+ ptx (* #DIA 1.50)) (+ pty (* #DIA 0.50)))
"A" "CE" (list (+ ptx (* #DIA 1.50)) (+ pty (* #DIA -1.50)))
(list (+ ptx 0.00) (+ pty (* #DIA -0.1771243444677)))
"CE" (list (+ ptx (* #DIA -1.50)) (+ pty (* #DIA -1.50)))
(list (+ ptx (* #DIA -1.50)) (+ pty (* #DIA 0.50)))
"L" (list (+ ptx (* #DIA -1.50)) (+ pty (* #DIA -0.50)))
"A" "A" -90.00 (list (+ ptx (* #DIA -0.50)) (+ pty (* #DIA -1.50)))
"L" (list (+ ptx (* #DIA 0.50)) (+ pty (* #DIA -1.50)))
"A" "A" -90.00 (list (+ ptx (* #DIA 1.50)) (+ pty (* #DIA -0.50)))
"L" "cl" nil)
       (ROTZ)
       (reset nil)
       (princ)
 )
;
;--------* 90 Deg Elbow (Up) Short Radius
;
(defun c:REL90SU ()
(inpnt)
(command "circle" (list (+ ptx 0.00) (+ pty 0.00))
(* #DIA 0.50) nil)
(setq ent (entlast))
(command "pline" (list (+ ptx (* #DIA -0.50)) (+ pty 0.00))
"W" 0.00 0.00 (list (+ ptx (* #DIA -0.50)) (+ pty (* #DIA -1.00)))
(list (+ ptx (* #DIA 0.50)) (+ pty (* #DIA -1.00)))
(list (+ ptx (* #DIA 0.50)) (+ pty 0.00)) nil)
(command "line" (list (+ ptx (* (/ #DIA 2) -0.7071067811))
(+ pty (* (/ #DIA 2) -0.7071067811)))
(list (+ ptx (* (/ #DIA 2) 0.7071067811))
(+ pty (* (/ #DIA 2) 0.7071067811))) nil)
(command "line" (list (+ ptx (* (/ #DIA 2) 0.7071067811))
(+ pty (* (/ #DIA 2) -0.7071067811)))
(list (+ ptx (* (/ #DIA 2) -0.7071067811))
(+ pty (* (/ #DIA 2) 0.7071067811))) nil)
(rotent)
(reset nil)
(princ)
)
;
;--------* 90 Deg Elbow (Down) Short Radius
;
(defun c:REL90SD ()
(inpnt)
(command "linetype" "S" "DASHED" nil)
(command "pline" (list (+ ptx (* #dia -0.50)) (+ pty 0.00))
"A" "A" 180.00 (list (+ ptx (* #dia 0.50)) (+ pty 0.00)) nil)
(setq ent (entlast))
(command "line" (list (+ ptx (* (/ #DIA 2) -0.7071067811))
(+ pty (* (/ #DIA 2) -0.7071067811)))
(list (+ ptx (* (/ #DIA 2) 0.7071067811))
(+ pty (* (/ #DIA 2) 0.7071067811))) nil)
(command "line" (list (+ ptx (* (/ #DIA 2) 0.7071067811))
(+ pty (* (/ #DIA 2) -0.7071067811)))
(list (+ ptx (* (/ #DIA 2) -0.7071067811))
(+ pty (* (/ #DIA 2) 0.7071067811))) nil)
(command "linetype" "S" "BYLAYER" nil)
(command "pline" (list (+ ptx (* #DIA -0.50)) (+ pty 0.00))
"W" 0.00 0.00 (list (+ ptx (* #DIA -0.50)) (+ pty (* #DIA -1.00)))
(list (+ ptx (* #DIA 0.50)) (+ pty (* #DIA -1.00)))
(list (+ ptx (* #DIA 0.50)) (+ pty 0.00))
"A" "A" 180.00 (list (+ ptx (* #DIA -0.50)) (+ pty 0.00))
"L" nil)
 (rotent)
 (reset nil)
 (princ)
)
;
;--------* 90 Deg Elbow (Up) Long Radius
;
(defun c:REL90LU ()
(inpnt)
(command "circle" (list (+ ptx 0.00) (+ pty 0.00))
(* #DIA 0.50) nil)
(setq ent (entlast))
(command "pline" (list (+ ptx (* #DIA -0.50)) (+ pty 0.00))
"W" 0.00 0.00 (list (+ ptx (* #DIA -0.50)) (+ pty (* #DIA -1.50)))
(list (+ ptx (* #DIA 0.50)) (+ pty (* #DIA -1.50)))
(list (+ ptx (* #DIA 0.50)) (+ pty 0.00)) nil)
(command "line" (list (+ ptx (* (/ #DIA 2) -0.7071067811))
(+ pty (* (/ #DIA 2) -0.7071067811)))
(list (+ ptx (* (/ #DIA 2) 0.7071067811))
(+ pty (* (/ #DIA 2) 0.7071067811))) nil)
(command "line" (list (+ ptx (* (/ #DIA 2) 0.7071067811))
(+ pty (* (/ #DIA 2) -0.7071067811)))
(list (+ ptx (* (/ #DIA 2) -0.7071067811))
(+ pty (* (/ #DIA 2) 0.7071067811))) nil)
 (rotent)
 (reset nil)
 (princ)
)
;
;--------* 90 Deg Elbow (Down) Long Radius
;
(defun c:REL90LD ()
(inpnt)
(command "linetype" "S" "DASHED" nil)
(command "pline" (list (+ ptx (* #dia -0.50)) (+ pty 0.00))
"A" "A" 180.00 (list (+ ptx (* #dia 0.50)) (+ pty 0.00)) nil)
(setq ent (entlast))
(command "line" (list (+ ptx (* (/ #DIA 2) -0.7071067811))
(+ pty (* (/ #DIA 2) -0.7071067811)))
(list (+ ptx (* (/ #DIA 2) 0.7071067811))
(+ pty (* (/ #DIA 2) 0.7071067811))) nil)
(command "line" (list (+ ptx (* (/ #DIA 2) 0.7071067811))
(+ pty (* (/ #DIA 2) -0.7071067811)))
(list (+ ptx (* (/ #DIA 2) -0.7071067811))
(+ pty (* (/ #DIA 2) 0.7071067811))) nil)
(command "linetype" "S" "BYLAYER" nil)
(command "pline" (list (+ ptx (* #DIA -0.50)) (+ pty 0.00))
"W" 0.00 0.00 (list (+ ptx (* #DIA -0.50)) (+ pty (* #DIA -1.50)))
(list (+ ptx (* #DIA 0.50)) (+ pty (* #DIA -1.50)))
(list (+ ptx (* #DIA 0.50)) (+ pty 0.00))
"A" "A" 180.00 (list (+ ptx (* #DIA -0.50)) (+ pty 0.00))
"L" nil)
 (rotent)
 (reset nil)
 (princ)
)
;
;--------* Tee (Side)
;
(defun c:RTEE ()
(inpnt)
(command "pline" (list (+ ptx (* #BDIA -0.50)) (+ pty (* #DIA 0.50)))
"W" 0.00 0.00 (list (+ ptx -4.00 (-(/ #BDIA 2))) (+ pty (* #DIA 0.50)))
(list (+ ptx -4.00 (-(/ #BDIA 2))) (+ pty (* #DIA -0.50)))
(list (+ ptx 4.00 (/ #BDIA 2)) (+ pty (* #DIA -0.50)))
(list (+ ptx 4.00 (/ #BDIA 2)) (+ pty (* #DIA 0.50)))
(list (+ ptx (* #BDIA 0.50)) (+ pty (* #DIA 0.50)))
(list (+ ptx (* #BDIA 0.50)) (+ pty 4.00 (/ #DIA 2)))
(list (+ ptx (* #BDIA -0.50)) (+ pty 4.00 (/ #DIA 2)))
(list (+ ptx (* #BDIA -0.50)) (+ pty (* #DIA 0.50)))
"A" "A" 106 (list (+ ptx (* #BDIA 0.50)) (+ pty (* #DIA 0.50)))
"L" nil)
  (ROTZ)
  (reset nil)
  (princ)
 )
;
;--------* Tee (Side Up)
;
(defun c:RTEES ()
(inpnt)
(command "pline" (list (+ ptx (* #BDIA 0.50)) (+ pty 0.00))
"W" 0.00 0.00 (list (+ ptx (* #BDIA 0.50)) (+ pty 4.00 (/ #DIA 2)))
(list (+ ptx (* #BDIA -0.50)) (+ pty 4.00 (/ #DIA 2)))
(list (+ ptx (* #BDIA -0.50)) (+ pty 0.00))
nil)
(command "circle" (list (+ ptx 0.00) (+ pty 0.00))
(* #DIA 0.50) nil)
(command "trim" "l" "" (list (+ ptx (* #BDIA 0.50)) (+ pty 0.00))
(list (+ ptx (* #BDIA -0.50)) (+ pty 0.00))
nil)
  (ROTZ)
  (reset nil)
  (princ)
 )
;
;--------* Tee (Down)
;
(defun c:RTEED ()
(inpnt)
(command "linetype" "S" "DASHED" nil)
(command "circle" (list (+ ptx 0.00) (+ pty 0.00))
(* #BDIA 0.50) nil)
(setq ent (entlast))
(command "line" (list (+ ptx (* (/ #BDIA 2) -0.7071067811))
(+ pty (* (/ #BDIA 2) -0.7071067811)))
(list (+ ptx (* (/ #BDIA 2) 0.7071067811))
(+ pty (* (/ #BDIA 2) 0.7071067811))) nil)
(command "line" (list (+ ptx (* (/ #BDIA 2) 0.7071067811))
(+ pty (* (/ #BDIA 2) -0.7071067811)))
(list (+ ptx (* (/ #BDIA 2) -0.7071067811))
(+ pty (* (/ #BDIA 2) 0.7071067811))) nil)
(command "linetype" "S" "BYLAYER" nil)
(command "pline" (list (+ ptx -4.00 (-(/ #BDIA 2))) (+ pty (-(/ #DIA 2))))
"W" 0.00 0.00 (list (+ ptx 4.00 (/ #BDIA 2)) (+ pty (-(/ #DIA 2))))
(list (+ ptx 4.00 (/ #BDIA 2)) (+ pty (/ #DIA 2)))
(list (+ ptx -4.00 (-(/ #BDIA 2))) (+ pty (/ #DIA 2)))
"cl" nil)
 (rotent)
 (reset nil)
 (princ)
)
;
;--------* Tee (Up)
;
(defun c:RTEEU ()
(inpnt)
(command "circle" (list (+ ptx 0.00) (+ pty 0.00))
(* #BDIA 0.50) nil)
(setq ent (entlast))
(command "line" (list (+ ptx (* (/ #BDIA 2) -0.7071067811))
(+ pty (* (/ #BDIA 2) -0.7071067811)))
(list (+ ptx (* (/ #BDIA 2) 0.7071067811))
(+ pty (* (/ #BDIA 2) 0.7071067811))) nil)
(command "line" (list (+ ptx (* (/ #BDIA 2) 0.7071067811))
(+ pty (* (/ #BDIA 2) -0.7071067811)))
(list (+ ptx (* (/ #BDIA 2) -0.7071067811))
(+ pty (* (/ #BDIA 2) 0.7071067811))) nil)
(command "pline" (list (+ ptx -4.00 (-(/ #BDIA 2))) (+ pty (-(/ #DIA 2))))
"W" 0.00 0.00 (list (+ ptx 4.00 (/ #BDIA 2)) (+ pty (-(/ #DIA 2))))
(list (+ ptx 4.00 (/ #BDIA 2)) (+ pty (/ #DIA 2)))
(list (+ ptx -4.00 (-(/ #BDIA 2))) (+ pty (/ #DIA 2)))
"cl" nil)
 (rotent)
 (reset nil)
 (princ)
)
;
;--------* Lateral (Left)
;
(defun c:RLATL ()
(inpnt)
(command "pline" (list (+ ptx (+ (* #BDIA -0.7071067811) (* #BDIA 0.50)))
                       (+ pty (* #DIA -0.50)))
"W" 0.00 0.00 (list (+ ptx (+ -3 (* #BDIA -0.7071067811) (* #BDIA 0.50)))
                    (+ pty (* #DIA -0.50)))
              (list (+ ptx (+ -3 (* #BDIA -0.7071067811) (* #BDIA 0.50)))
                    (+ pty (* #DIA 0.50)))
              (list (+ ptx (+ 3 (* #BDIA 0.7071067811) (* #BDIA 0.50)))
                    (+ pty (* #DIA 0.50)))
              (list (+ ptx (+ 3 (* #BDIA 0.7071067811) (* #BDIA 0.50)))
                    (+ pty (* #DIA -0.50)))
      (setq p (list (+ ptx (* #BDIA 0.7071067811) (* #BDIA 0.50))
                    (+ pty (* #DIA -0.50))))
      (setq p (polar p 5.49778714 3.00))
              (polar p 3.92699082 #BDIA)
              (list (+ ptx (+ (* #BDIA -0.7071067811) (* #BDIA 0.50)))
                    (+ pty (* #DIA -0.50)))
"A" "A" -39.00 (list (+ ptx (* #BDIA 0.7071067811) (* #BDIA 0.50))
                    (+ pty (* #DIA -0.50)))
nil)
(command "_.mirror" "l" "" pt "@0.1<90" "Y")
  (ROTZ)
  (reset nil)
  (princ)
 )
;
;--------* Lateral (Right)
;
(defun c:RLATR ()
(inpnt)
(command "pline" (list (+ ptx (+ (* #BDIA -0.7071067811) (* #BDIA 0.50)))
                       (+ pty (* #DIA -0.50)))
"W" 0.00 0.00 (list (+ ptx (+ -3 (* #BDIA -0.7071067811) (* #BDIA 0.50)))
                    (+ pty (* #DIA -0.50)))
              (list (+ ptx (+ -3 (* #BDIA -0.7071067811) (* #BDIA 0.50)))
                    (+ pty (* #DIA 0.50)))
              (list (+ ptx (+ 3 (* #BDIA 0.7071067811) (* #BDIA 0.50)))
                    (+ pty (* #DIA 0.50)))
              (list (+ ptx (+ 3 (* #BDIA 0.7071067811) (* #BDIA 0.50)))
                    (+ pty (* #DIA -0.50)))
      (setq p (list (+ ptx (* #BDIA 0.7071067811) (* #BDIA 0.50))
                    (+ pty (* #DIA -0.50))))
      (setq p (polar p 5.49778714 3.00))
              (polar p 3.92699082 #BDIA)
              (list (+ ptx (+ (* #BDIA -0.7071067811) (* #BDIA 0.50)))
                    (+ pty (* #DIA -0.50)))
"A" "A" -39.00 (list (+ ptx (* #BDIA 0.7071067811) (* #BDIA 0.50))
                    (+ pty (* #DIA -0.50)))
nil)
  (ROTZ)
  (reset nil)
  (princ)
 )
;
;--------* Concentric Reducer
;
(defun c:RREDC ()
(inpnt)
(command "pline" (list (+ ptx 0.00) (+ pty (* #DIA 0.50)))
"W" 0.00 0.00 (setq p (list (+ ptx 0.00) (+ pty (* #DIA -0.50))))
(setq p (polar p 0.26179938 (* 1.9318525563 (- #DIA #BDIA))))
(polar p 1.57079628 #BDIA) "cl" nil)
(setq ent (entlast))
 (rotent)
 (reset nil)
 (princ)
 )
;
;--------* Eccentric Reducer (Left)
;
(defun c:RREDEL ()
(inpnt)
(command "pline" (list (+ ptx 0.00) (+ pty (* #DIA 0.50)))
"W" 0.00 0.00 (setq p (list (+ ptx 0.00) (+ pty (* #DIA -0.50))))
(setq p (polar p 2.61799389 (* 2.00 (- #DIA #BDIA))))
(polar p 1.57079628 #BDIA) "cl" nil)
(setq ent (entlast))
 (rotent)
 (reset nil)
 (princ)
 )
;
;--------* Eccentric Reducer (Right)
;
(defun c:RREDER ()
(inpnt)
(command "pline" (list (+ ptx 0.00) (+ pty (* #DIA 0.50)))
"W" 0.00 0.00 (setq p (list (+ ptx 0.00) (+ pty (* #DIA -0.50))))
(setq p (polar p 0.52359876 (* 2.00 (- #DIA #BDIA))))
(polar p 1.57079628 #BDIA) "cl" nil)
(setq ent (entlast))
 ;(trnsfm)
 (rotent)
 (reset nil)
 (princ)
 )
;
;--------* Diameter of duct fitting
;
;(defun dia ()
;  (initget (+ 1 2 4))
;  (setq #dia (getint "\nEnter diameter of duct: "))
; )
;
;--------* Branch diameter prompt
;
;(defun bdia ()
;  (initget (+ 1 2 4))
;  (setq #bdia (getint "\nEnter diameter of branch duct: "))
; )
;
;--------* insertion point prompt
;
(defun inpnt ()
  (setvar "osmode" h_osm)
  (setq pt (getpoint "\nSelect Insertion point: "))
  (setvar "osmode" 0)
  (setq ptx (car  pt)
        pty (cadr pt)
        stmp (ssadd)
  )
)
;
;--------* rotate about z axis
;
(defun ROTZ ()
  (setvar "osmode" h_osm)
  (prompt "\nRotation angle: ")
  (command "rotate" (entlast) "" pt pause)
)
;
;--------* rotate entity function
;
(defun rotent ()
  (setvar "osmode" h_osm)
  (while ent
           (ssadd ent stmp)
           (setq ent (entnext ent))
  )
  (command "rotate" stmp "" pt pause)
 (setq stmp nil)
)
(princ)
