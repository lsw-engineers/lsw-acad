;------------------------<<  Begin Support Functions  >>------------------------

; ------------  PLACE THE LSWELEC PULL-DOWN FUNCTION -------------
;  This function places the LSWELEC pull-down to the left of the
;  Window pull-down on the acad menu. If FLG is true the current
;  LSWELEC pull-down if present will be removed and placed again.
;  If FLG is nil and the pull-down is present, nothing will be done
;
;  When placing the LSWELEC menu, acad's Window menu is used to
;  determine the pull-down location. if the Window pull-down is
;  missing, the Help pull-down will be used instead. If that too
;  is missing, it will place the LSWELEC pull-down after the last
;  menu location.
; ----------------------------------------------------------------

; Place the LSWELEC Tools pulldown to the left of the last pulldown already loaded
(defun lswelec-placemenu( / n )
  (if (menugroup "LSWELEC")
      (progn
       (setq n 1)
       (while (< n 24)
        (if (menucmd (strcat "P" (itoa n) ".1=?"))
	    (setq n (+ n 1))
            (progn
             (if (> n 3)
                 (setq n (- n 2))
                 (setq n 3)
             );if
             (menucmd (strcat "p" (itoa n) "=+LSWELEC.pop8"))
             (menucmd (strcat "p" (itoa n) "=+LSWELEC.pop7"))
             (menucmd (strcat "p" (itoa n) "=+LSWELEC.pop6"))
             (menucmd (strcat "p" (itoa n) "=+LSWELEC.pop5"))
             (menucmd (strcat "p" (itoa n) "=+LSWELEC.pop4"))
             (menucmd (strcat "p" (itoa n) "=+LSWELEC.pop3"))
             (menucmd (strcat "p" (itoa n) "=+LSWELEC.pop2"))
             (menucmd (strcat "p" (itoa n) "=+LSWELEC.pop1"))
             (setq n 25)
            );progn
        );if
       );while
      );progn
  );if
);defun lswelec-placemenu
 
(lswelec-placemenu)

(defun inblk (blknm)
     (command "insert" blknm "s" edwgsc pause pause)
(princ))

(defun inschd (schd / AR AD)
     (prompt "\nPick insertion point of Schedule: ")
     (setq AR (getvar "attreq"))
     (setq AD (getvar "attdia"))
     (setvar "attreq" 0)
     (setvar "attdia" 0)
     (command "insert" schd "s" dwgsc pause 0)
     (setvar "attreq" AR)
     (setvar "attdia" AD)
(princ))

(load"fadesign.lsp")

(defun insert_symbol_perpendicular	(block		  description
							 layer		  /
							 block_angle	  condition
							 input_point	  insertion_point
							 block_angle	  entity_pointer
							)
  (F:SLAY layer)
  (F:MODS
    (quote ("cmdecho" "osmode"))
  )
  (setvar "cmdecho" 0)
  (setvar "osmode" 0)

  (setq input_point "")

  (while (setq	input_point
		 (getpoint
		   (strcat "\nSpecify insertion point for '"
				 description
				 "' (Enter when done): "
		   )
		 )
		)

	   (setq insertion_point nil)

	   (if (vl-cmdf "ID" "NEAR" input_point)
		(progn

		  (setq insertion_point (getvar "lastpoint"))

		  (setq block_angle
			    (R->D (angle insertion_point input_point))
		  )

		  (command "INSERT"
				 block
				 insertion_point
				 (SCALEFACTOR)
				 (SCALEFACTOR)
				 block_angle
		  )

								;Fix attributes

		  (setq entity_pointer (entlast))

		  (setq entity_data (entget entity_pointer))

		  (setq condition T)

		  (while condition
		    (if (= (cdr (assoc 0 entity_data)) "ATTRIB")
			 (progn
			   (setq condition nil)
			   (setq entity_data
					(subst (cons 50 0.0)
						  (assoc 50 entity_data)
						  entity_data
					)
			   )
;;;	          (setq entity_data
;;;		         (subst (cons 62 7)
;;;			        (assoc 62 entity_data)
;;;			        entity_data
;;;		         )
;;;	          )
			   (entmod entity_data)
			   (entupd entity_pointer)
			 ) ;_ end of progn
			 (progn
			   (setq entity_pointer (entnext entity_pointer))
			   (if entity_pointer
				(setq entity_data (entget entity_pointer))
				(setq condition nil)
			   ) ;_ end of if
			 ) ;_ end of progn
		    ) ;_ end of if

		  ) ;_ end of while (fix attributes)

		) ;_ end of if->true progn (valid near point)

		(command)					;cancels "ID" command

	   ) ;_ end of if (near point)

  ) ;_ end of while (insersion loop)

   (prompt " Done.  Exiting...")
   
  (F:MODR)
  (F:RLAY)
  (princ)
)

;------------------------<< Begin Electrical Commands >>------------------------

(defun c:1G ()
     (f:slay "EP-CIRC-NEW")
     (command "insert" "pow1g" "s" edwgsc "qui,nea" pause pause)
(f:rlay)
(princ))

(defun c:1H ()
     (f:slay "EP-CIRC-NEW")
     (command "insert" "pow1h" "s" edwgsc "qui,nea" pause pause)
(f:rlay)
(princ))

(defun c:1N ()
     (f:slay "EP-CIRC-NEW")
     (command "insert" "pow1n" "s" edwgsc "qui,nea" pause pause)
(f:rlay)
(princ))


(defun c:2 ()
     (f:slay "EP-CIRC-NEW")
     (command "insert" "pow2" "s" edwgsc "qui,nea" pause pause)
(f:rlay)
(princ))

(defun c:220 ()
     (prompt "\nNow inserting 'special purpose receptacle:' ")
     (setvar "orthomode" 1)
     (f:slay "EP-WALL-NEW")
     (command "insert" "pow33" "s" edwgsc pause pause)
(f:rlay)
(princ))

(defun c:2G ()
     (f:slay "EP-CIRC-NEW")
     (command "insert" "pow2g" "s" edwgsc "qui,nea" pause pause)
(f:rlay)
(princ))

(defun c:2G2 ()
     (f:slay "EP-CIRC-NEW")
     (command "insert" "pow2g2" "s" edwgsc "qui,nea" pause pause)
(f:rlay)
(princ))


(defun c:2ST ()
     (prompt "\nNow inserting 2' strip light: ")
     (f:slay "EL-CLNG-NEW")
     (setvar "orthomode" 1)
     (command "insert" "strip2" "s" 1 pause pause)
(f:rlay)
(princ))

(defun c:2STJ ()
     (prompt "\nNow inserting 2' strip light with j-box: ")
     (f:slay "EL-CLNG-NEW")
     (setvar "orthomode" 1)
     (command "insert" "strip2j" "s" 1 pause pause)
(f:rlay)
(princ))

(defun c:3 ()
     (f:slay "EP-CIRC-NEW")
     (command "insert" "pow3" "s" edwgsc "qui,nea" pause pause)
(f:rlay)
(princ))

(defun c:3G ()
     (f:slay "EP-CIRC-NEW")
     (command "insert" "pow3g" "s" edwgsc "qui,nea" pause pause)
(f:rlay)

(princ))
(defun c:3G3 ()
     (f:slay "EP-CIRC-NEW")
     (command "insert" "pow3g3" "s" edwgsc "qui,nea" pause pause)
(f:rlay)
(princ))


(defun c:3ST ()
     (prompt "\nNow inserting 3' strip light: ")
     (f:slay "EL-CLNG-NEW")
     (setvar "orthomode" 1)
     (command "insert" "strip3" "s" 1 pause pause)
(f:rlay)
(princ))

(defun c:3STJ ()
     (prompt "\nNow inserting 3' strip light with j-box: ")
     (f:slay "EL-CLNG-NEW")
     (setvar "orthomode" 1)
     (command "insert" "strip3j" "s" 1 pause pause)
(f:rlay)
(princ))

(defun c:4 ()
     (f:slay "EP-CIRC-NEW")
     (command "insert" "pow4" "s" edwgsc "qui,nea" pause pause)
(f:rlay)
(princ))

(defun c:4G ()
     (f:slay "EP-CIRC-NEW")
     (command "insert" "pow4g" "s" edwgsc "qui,nea" pause pause)
(f:rlay)
(princ))


(defun c:4ST ()
     (prompt "\nNow inserting 4' strip light: ")
     (f:slay "EL-CLNG-NEW")
     (setvar "orthomode" 1)
     (command "insert" "strip4" "s" 1 pause pause)
(f:rlay)
(princ))

(defun c:4STJ ()
     (prompt "\nNow inserting 4' strip light with j-box: ")
     (f:slay "EL-CLNG-NEW")
     (setvar "orthomode" 1)
     (command "insert" "strip4j" "s" 1 pause pause)
(f:rlay)
(princ))

(defun c:5 ()
     (f:slay "EP-CIRC-NEW")
     (command "insert" "pow5" "s" edwgsc "qui,nea" pause pause)
(f:rlay)
(princ))

(defun c:5G ()
     (f:slay "EP-CIRC-NEW")
     (command "insert" "pow5g" "s" edwgsc "qui,nea" pause pause)
(f:rlay)
(princ))

(defun c:6 ()
     (f:slay "EP-CIRC-NEW")
     (command "insert" "pow6" "s" edwgsc "qui,end" pause pause)
(f:rlay)
(princ))

(defun c:6ST ()
     (prompt "\nNow inserting 6' strip light: ")
     (f:slay "EL-CLNG-NEW")
     (setvar "orthomode" 1)
     (command "insert" "strip6" "s" 1 pause pause)
(f:rlay)
(princ))

(defun c:6STJ ()
     (prompt "\nNow inserting 6' strip light with j-box: ")
     (f:slay "EL-CLNG-NEW")
     (setvar "orthomode" 1)
     (command "insert" "strip6j" "s" 1 pause pause)
(f:rlay)
(princ))

(defun c:8ST ()
     (prompt "\nNow inserting 8' strip light: ")
     (f:slay "EL-CLNG-NEW")
     (setvar "orthomode" 1)
     (command "insert" "strip8" "s" 1 pause pause)
(f:rlay)
(princ))

(defun c:8STJ ()
     (prompt "\nNow inserting 8' strip light with j-box: ")
     (f:slay "EL-CLNG-NEW")
     (setvar "orthomode" 1)
     (command "insert" "strip8j" "s" 1 pause pause)
(f:rlay)
(princ))

(defun c:AZ ()
     (f:slay "NOTE-NEW")
     (setvar "osmode" 1536)
     (setq pt1a (getpoint "first point of line <arrow end>: "))
     ;(setq pt1a (osnap pt1 "qui,nea"))
     (setvar "osmode" 0)
     (prompt "second point of line <top>: ")
     (command "line" pt1a "qui,perp" pause "")
     (command "insert" "arroa" "s" dwgsc "r" 90.00 pt1a)
(f:rlay)
(princ))

(defun c:BRC (/ ce ss pt no ls)
(command "undo" "group")
(setq pta (getpoint "\npick symbol: <insert of> "))
(setq pt (osnap pta "qui,ins"))
(command "circle" pt (* dwgsc 0.0625))
(setq ce (ssget "l"))
(prompt "pick item to break: ")
(command "select" "single" pause)
(setq ss (ssget "p"))
(setq ls (sslength ss))
(setq no -1)
(command "trim" ce "")
(repeat ls
  (setq no (1+ no))
 (command (list (ssname ss no) pt)))
(command "")
(command "erase" ce "")
(command "undo" "end")
(princ))

(defun c:CAM ()
     (prompt "\nNow inserting 'Camera:' ")
     (setvar "orthomode" 1)
     (f:slay "SS-CLNG-NEW")
     (command "insert" "camera" "s" edwgsc "qui,nea" pause pause)
(f:rlay)
(princ))

(defun c:CAP ()
     (prompt "\nNow inserting 'conduit cap:' ")
     (f:slay "EP-CIRC-NEW")
     (command "insert" "cap" "s" edwgsc "qui,end" pause pause)
(f:rlay)
(princ))

(defun c:CB ()
     (f:slay "EO-DIST-NEW")
     (prompt "\nNow inserting 'el5' (circuit breaker symbol): ")
     (setq amp (cond ((> amp "") amp)(t "")))
     (setq in1 (getstring
          (strcat "\nAmpacity/poles? <" amp ">: ") t)
     amp (cond ((= in1 " ") "")((> in1 "") in1)(t amp)))
     (command "insert" "el5" "s" edwgsc "r" 0 pause amp)
(f:rlay)
(princ))

(defun c:CB1 ()
     (f:slay "NOTE-NEW")
     (setq amp (cond ((> amp "") amp)(t "")))
     (setq in1 (getstring
          (strcat "\nwhat is the amperage of the c.b. ? <" amp ">: ") t)
     amp (cond ((= in1 " ") "")((> in1 "") in1)(t amp)))
     (command "insert" "cb1" "s" edwgsc "r" 0 "qui,int" pause amp)
(princ))

(defun c:CB2 ()
     (f:slay "NOTE-NEW")
     (setq amp (cond ((> amp "") amp)(t "")))
     (setq in1 (getstring
          (strcat "\nwhat is the amperage of the c.b. ? <" amp ">: ") t)
     amp (cond ((= in1 " ") "")((> in1 "") in1)(t amp)))
     (command "insert" "cb2" "s" edwgsc "r" 0 "qui,int" pause amp)
(f:rlay)
(princ))

(defun c:CB3 ()
     (f:slay "NOTE-NEW")
     (setq amp (cond ((> amp "") amp)(t "")))
     (setq in1 (getstring
          (strcat "\nwhat is the amperage of the c.b. ? <" amp ">: ") t)
     amp (cond ((= in1 " ") "")((> in1 "") in1)(t amp)))
     (command "insert" "cb3" "s" edwgsc "r" 0 "qui,int" pause amp)
(f:rlay)
(princ))

(defun c:CD ()
(setvar "cmdecho" 0)
(setq orth (getvar "orthomode"))
(setvar "orthomode" 0)
(f:slay "EP-CIRC-NEW")
(setvar "skpoly" 1)
(prompt "\sketch line of conduit, strike return or space when complete:")
(command "sketch" (* dwgsc 0.125))
(command "pedit" "l" "s" "")
(setvar "orthomode" orth)
(princ))

(defun c:CLCON ()
(f:slay "EO-DIST-NEW")
(princ "pick entity to insert closed (solid) connection symbol at end of: ")
(command "insert" "el3" "s" edwgsc "qui,end" pause pause)
(f:rlay)
(princ))

(defun c:CLCT ()
(f:slay "EO-DIST-NEW")
(princ "pick entity to insert closed contact symbol at end of: ")
(command "insert" "clct" "s" edwgsc "r" 0 pause)
(f:rlay)
(princ))

(defun c:CLOCK ()
     (prompt "\nNow inserting 'clock:' ")
     (setvar "orthomode" 1)
     (f:slay "SS-WALL-NEW")
     (command "insert" "pow49" "s" edwgsc "qui,nea" pause pause)
(f:rlay)
(princ))

(defun c:CNT ()
     (prompt "\nNow inserting 'Contactor Symbol:' ")
     (setvar "orthomode" 1)
     (f:slay "EP-WALL-NEW")
     (command "insert" "pow17" "s" edwgsc "r" 0 pause)
(f:rlay)
(princ))

(defun c:D ()
     (prompt "\nNow inserting 'Data outlet <hollow> :' ")
     (setvar "orthomode" 1)
     (f:slay "SS-WALL-NEW")
     (command "insert" "pow39" "s" edwgsc "qui,nea" pause pause)
(f:rlay)
(princ))

(defun C:DATA ()
(C:D)
(PRINC))

(defun C:DIMR ()
     (prompt "\nNow Inserting 'Dimmer Switch:' ")
     (f:slay "EP-WALL-NEW")
     (setvar "orthomode" 1)
     (inblk "pow16")
(f:rlay)
(princ))

(defun c:DLT ()
     (prompt "\nNow inserting Downlight fixture: ")
     (f:slay "EL-CLNG-NEW")
     (setvar "orthomode" 1)
     (setq DLT (cond ((> DLT "") DLT)(T "")))
  (setq DLTa (getstring
      (strcat "\nEnter Fixture number <" DLT "> ? "))
    DLT (cond ((= DLTa " ") "")((> DLTa "") DLTa)(T DLT)))
     (prompt "\nPick insertion point and then place fixture tag: ")
     (command "insert" "incan" "s" edwgsc "qui,nea" "r" 0 pause)
     (command "insert" "tag1" "s" dwgsc "r" 0 (getvar "lastpoint") DLT)
     (command "change" "l" "" "p" "la" "note-new" "")
     (setvar "orthomode" 0)
     (command "move" "l" "" (getvar "lastpoint") pause)
(f:rlay)
(princ))

(defun c:DLS ()
     (prompt "\nNow inserting Sconce fixture: ")
     (f:slay "EL-CLNG-NEW")
     (setvar "orthomode" 1)
     (setq DLS (cond ((> DLS "") DLS)(T "")))
  (setq DLSa (getstring
      (strcat "\nEnter Fixture number <" DLS "> ? "))
    DLS (cond ((= DLSa " ") "")((> DLSa "") DLSa)(T DLS)))
     (prompt "Place fixture, rotate bracket to correct orientation, then move tag to correct location: " )
     (command "insert" "incanA" "s" edwgsc "r" 0 pause)
     (command "erase" "l" "")
     (command "insert" "incan" "s" edwgsc "r" 0 (getvar "lastpoint"))
     (command "insert" "exit-mt" "s" edwgsc (getvar "lastpoint") pause)
     (command "insert" "tag1" "s" dwgsc "r" 0 (getvar "lastpoint") DLS)
     (command "change" "l" "" "p" "la" "note-new" "")
     (setvar "orthomode" 0)
     (command "move" "l" "" (getvar "lastpoint") pause)
(f:rlay)
(princ))

(defun c:DLW ()
     (prompt "\nNow inserting Wall Wash fixture: ")
     (f:slay "EL-CLNG-NEW")
     (setvar "orthomode" 1)
     (setq DLW (cond ((> DLW "") DLW)(T "")))
  (setq DLWa (getstring
      (strcat "\nEnter Fixture number <" DLW "> ? "))
    DLW (cond ((= DLWa " ") "")((> DLWa "") DLWa)(T DLW)))
     (prompt "Place fixture rotate to correct orientation, then move tag to correct location: " )
     (command "insert" "wallwash" "s" edwgsc pause pause)
     (command "insert" "tag1" "s" dwgsc "r" 0 (getvar "lastpoint") DLW)
     (command "change" "l" "" "p" "la" "note-new" "")
     (setvar "orthomode" 0)
     (command "move" "l" "" (getvar "lastpoint") pause)
(f:rlay)
(princ))

(defun c:DN ()
     (f:slay "EP-CIRC-NEW")
     (command "insert" "cnddown" "s" edwgsc "qui,end" pause pause)
     (f:rlay)
(princ))

(defun c:DPUSH ()
     (prompt "\nNow inserting 'Double Pushbutton:' ")
     (setvar "orthomode" 1)
     (f:slay "EP-WALL-NEW")
     (command "insert" "pow48" "s" edwgsc pause pause)
(f:rlay)
(princ))

(defun c:DRAWOUT ()
(f:slay "EO-DIST-NEW")
(princ "pick entity to insert draw out stabs at end of: ")
(command "insert" "pow53" "s" edwgsc "qui,end" pause pause)
(f:rlay)
(princ))

(defun c:EC ()
     (f:slay "NOTE-NEW")
     (F:MODS (QUOTE ("attreq")))
     (setvar "attreq" 1)
     (command "undo" "group")
     (setq
     epfx (cond ((> epfx "") epfx)(t "")))  ; 
     (setq
          ein1 (getstring
          (strcat "\nconduit tag text <" epfx ">: ") t)
     epfx (cond ((= ein1 " ") "")((> ein1 "") ein1)(t epfx)))
     (setq pta (getpoint "\npick conduit tag insertion point: "))
     (setq pt (osnap pta "qui,nea"))
     (command "circle" pt (getvar "textsize"))
     (setq cs (ssget "l"))
     (command "select" "single" pta)
     (setq ss (ssget "p"))
     (command "trim" ss "" pt "")
     (setvar "cmdecho" 1)
     (command "erase" cs "")
     (command "insert" "cdttag" "s" (getvar "textsize") pt "0" epfx)
     (command "undo" "end")
(f:rlay)
(f:modr)
(setvar "cmdecho" 0)
(princ))

(defun c:EL1 ()
(f:slay "EO-DIST-NEW")
     (prompt "\nNow inserting 'el1' (transformer symbol): ")
     (setq kva (getstring "\nKVA rating of transformer (i.e. 30.00, 45.00, 75.00, 112.5, 250.0 etc) ? "))
     (setq pri (getstring "\nPrimary voltage, configuration (default: 480V, 3PH, 3W DELTA) ? "))
     (setq sec (getstring "\nSecondary voltage, configuration (default: 208/120V, 3PH, 4W WYE) ? "))
     (prompt "\nPick insertion point of transformer: ")
     (command "insert" "el1" "s" edwgsc pause 0 kva pri sec)
(f:rlay)
(princ))

(defun c:EL2 ()
     (f:slay "EO-DIST-NEW")
     (prompt "\nNow inserting 'el2' (ground symbol): ")
     (inblk "el2")
(f:rlay)
(princ))

(defun c:EL3 ()
(f:slay "EO-DIST-NEW")
(princ "pick entity to insert el3 (line bolted symbol) at end of: ")
(command "insert" "el3" "s" edwgsc "qui,end" pause pause)
(f:rlay)
(princ))

(defun c:EL3A ()
(f:slay "EO-DIST-NEW")
(princ "pick entity to insert el3a (open circle connection) at end of: ")
(command "insert" "el3a" "s" edwgsc "qui,end" pause "")
(f:rlay)
(princ))

(defun c:EL4 ()
     (f:slay "EO-DIST-NEW")
     (prompt "\nNow inserting 'el4' (meter w/ c.t.'s symbol): ")
     (inblk "el4")
(f:rlay)
(princ))

(defun c:EL5 ()
     (f:slay "EO-DIST-NEW")
     (prompt "\nNow inserting 'el5' (Circuit Breaker symbol): ")
     (setq amp (cond ((> amp "") amp)(t "")))
     (setq in1 (getstring
          (strcat "\nAmpacity/poles? <" amp ">: ") t)
     amp (cond ((= in1 " ") "")((> in1 "") in1)(t amp)))
     (command "insert" "el5" "s" edwgsc "r" 0 pause amp)
(f:rlay)
(princ))

(defun c:EL6 ()
     (prompt "\nNow inserting 'el6' (fused disc. switch symbol): ")
     (setq swa (getstring "\nAmpacity and Pole count of switch (default: 30/3) ? "))
     (setq fua (getstring "\nAmpacity of fuse (default: 30A) ? "))
     (setq clf (getstring "\nClass of fuse (default: LPS-RK) ? "))
     (command "insert" "el6" "s" edwgsc pause 0 swa fua clf)
(f:rlay)
(princ))

(defun c:EL7 ()
     (f:slay "EO-DIST-NEW")
     (prompt "\nNow inserting 'el7': ")
     (inblk "el7")
(f:rlay)
(princ))

(defun c:EL8 ()
     (prompt "\nNow inserting 'el8' (node point symbol): ")
     (f:slay "EO-NODE-NEW")
     (setq EL8 (cond ((> EL8 "") EL8)(T "")))
  (setq EL8a (getstring
      (strcat "\nAvailable Fault Amps <" EL8 "> ? "))
    EL8 (cond ((= EL8a " ") "")((> EL8a "") EL8a)(T EL8)))
     (prompt "\nPick insertion point:")
     (command "insert" "el8" "s" edwgsc "r" 0 "qui,nea" pause EL8)
(f:rlay)
(princ))

(defun c:EL9 ()
(command "osnap" "qui,end")
     (prompt "\nNow inserting 'el9' (panelboard symbol): ")
     (f:slay "EO-DIST-NEW")
     (command "insert" "el9" "s" edwgsc pause 0)
(f:rlay)
(setvar "osmode" 0)
(princ))

(defun c:EM14 ()
     (prompt "\nNow inserting 1'x4' emergency indicator: ")
     (f:slay "EL-CLNG-NEW")
     (setvar "orthomode" 1)
     (command "insert" "fill14" "s" 1 "qui,end" pause pause)
(f:rlay)
(princ))

(defun c:EM2 ()
     (prompt "\nNow inserting 2' emergency strip: ")
     (f:slay "EL-CLNG-NEW")
     (setvar "orthomode" 1)
     (command "insert" "emstrip2" "s" "qui,end" 1 pause pause)
(f:rlay)
(princ))

(defun c:EM22 ()
     (prompt "\nNow inserting 2'x2' emergency indicator: ")
     (f:slay "EL-CLNG-NEW")
     (setvar "orthomode" 1)
     (command "insert" "fill22" "s" 1 "qui,end" pause pause)
(f:rlay)
(princ))

(defun c:EM24 ()
     (prompt "\nNow inserting 2'x4' emergency indicator: ")
     (f:slay "EL-CLNG-NEW")
     (setvar "orthomode" 1)
     (command "insert" "fill24" "s" 1 "qui,end" pause pause)
(f:rlay)
(princ))

(defun c:EM3 ()
     (prompt "\nNow inserting 3' emergency strip: ")
     (f:slay "EL-CLNG-NEW")
     (setvar "orthomode" 1)
     (command "insert" "emstrip3" "s" 1 pause pause)
(f:rlay)
(princ))

(defun c:EM4 ()
     (prompt "\nNow inserting 4' emergency strip: ")
     (f:slay "EL-CLNG-NEW")
     (setvar "orthomode" 1)
     (command "insert" "emstrip4" "s" 1 pause pause)
(f:rlay)
(princ))

(defun c:EM6 ()
     (prompt "\nNow inserting 6' emergency strip: ")
     (f:slay "EL-CLNG-NEW")
     (setvar "orthomode" 1)
     (command "insert" "emstrip6" "s" 1 pause pause)
(f:rlay)
(princ))

(defun c:EM8 ()
     (prompt "\nNow inserting 8' emergency strip: ")
     (f:slay "EL-CLNG-NEW")
     (setvar "orthomode" 1)
     (command "insert" "emstrip8" "s" 1 pause pause)
(f:rlay)
(princ))

(defun c:EMDI ()
     (prompt "\nNow inserting emergency downlight symbol: ")
     (f:slay "EL-CLNG-NEW")
     (setvar "orthomode" 1)
     (command "insert" "emdnlt" "s" edwgsc "qui,cen" pause pause)
(f:rlay)
(princ))

(defun c:EMERG ()
     (prompt "\nNow inserting emergency wall-pack symbol: ")
     (f:slay "EL-WALL-NEW")
     (setvar "orthomode" 1)
     (command "insert" "emerg" "s" edwgsc "qui,nea" pause pause)
(f:rlay)
(princ))

(defun c:EMIOUT ()
     (prompt "\nNow inserting 'emergency isolated ground duplex receptacle:' ")
     (setvar "orthomode" 1)
     (f:slay "EP-WALL-NEW")
     (command "insert" "emisodup" "s" edwgsc pause pause)
(f:rlay)
(princ))

(defun c:EMIQUAD ()
     (prompt "\nNow inserting 'emergency isolated ground quadruplex receptacle:' ")
     (setvar "orthomode" 1)
     (f:slay "EP-WALL-NEW")
     (command "insert" "emisoqd" "s" edwgsc pause pause)
(f:rlay)
(princ))

(defun c:EMJ ()
     (f:slay "EP-ECKT-NEW")
     (command "insert" "emj" "s" edwgsc "r" 0 pause)
(f:rlay)
(princ))

(defun c:EMOUT ()
     (prompt "\nNow inserting 'emergency duplex receptacle:' ")
     (setvar "orthomode" 1)
     (f:slay "EP-WALL-NEW")
     (command "insert" "pow34" "s" edwgsc pause pause)
(f:rlay)
(princ))

(defun c:EMQUAD ()
     (prompt "\nNow inserting 'emergency quadruplex receptacle:' ")
     (setvar "orthomode" 1)
     (f:slay "EP-WALL-NEW")
     (command "insert" "pow70" "s" edwgsc pause pause)
(f:rlay)
(princ))

(defun c:EMSIMP ()
     (prompt "\nNow inserting 'emergency simplex receptacle:' ")
     (setvar "orthomode" 1)
     (f:slay "EP-WALL-NEW")
     (command "insert" "pow67" "s" edwgsc pause pause)
(f:rlay)
(princ))

(defun c:EMSPEC ()
     (prompt "\nNow inserting 'emergency special purpose receptacle:' ")
     (setvar "orthomode" 1)
     (f:slay "EP-WALL-NEW")
     (command "insert" "pow33em" "s" edwgsc pause pause)
(f:rlay)
(princ))

(defun c:ESE ()
     (f:slay "EP-ECKT-NEW")
     (setq ort (getvar "orthomode"))
     (setvar "orthomode" 0)
     (setvar "cmdecho" 1)
     (command "arc" "qui,nea" pause "e" "qui,nea" pause "d" pause)
     (f:rlay)
     (setvar "orthomode" ort)
(princ))

(defun c:ESED2 (/ pnt1 pnt2 cir1 cir2 om)
     (f:slay "EP-ECKT-NEW")
     (F:MODS (QUOTE ("orthomode" "osmode")))
     (command "undo" "m")
     (setvar "orthomode" 0)
     (command "osnap" "qua")
     (setq pnt1 (getpoint "\nBeginning arc point: "))
     (setq pnt2 (getpoint "\nEnding arc point: "))
     (command "osnap" "non")
     (command "circle" "cen" pnt1 "qua" pnt1)
     (setq cir1 (entlast))
     (command "circle" "cen" pnt2 "qua" pnt2)
     (setq cir2 (entlast))
     (command "arc" "cen" pnt1 "e" "cen" pnt2 "d" pause)
     (command "trim" "auto" cir1 "" "cen" pnt1 "")
     (command "trim" "auto" cir2 "" "cen" pnt2 "")
     (command "erase" cir1 cir2 "")
     (command "redraw")
(f:modr)
(f:rlay)
(princ))

(defun c:EXA ()
     (prompt "now inserting 'exit light directional arrow:' ")
     (f:slay "EL-CLNG-NEW")
     (setvar "orthomode" 1)
     (command "insert" "exitarr" "s" edwgsc pause pause)
(f:rlay)
(princ))

(defun c:EXE ()
     (layerset  "EP-EQPM-EXST")
(princ))

(defun c:EXIT ()
     (prompt "\nNow inserting 'Single Face exit light:' ")
     (setvar "orthomode" 1)
     (f:slay "EL-CLNG-NEW")
     (setq X1 (cond ((> X1 "") X1)(T "")))
  (setq X1a (getstring
      (strcat "\nEnter Fixture number <" X1 "> ? "))
    X1 (cond ((= X1a " ") "")((> X1a "") X1a)(T X1)))
     (prompt "Place fixture, rotate bracket to correct orientation, then move callout to correct location" )
     (command "insert" "exitA" "s" edwgsc "r" 0 pause)
     (command "erase" "l" "")
     (command "insert" "exit" "s" edwgsc (getvar "lastpoint") pause)
     (command "insert" "exit-mt" "s" edwgsc (getvar "lastpoint") pause)
     (setvar "orthomode" 0)
     (command "insert" "tag1" "s" dwgsc "r" 0 (getvar "lastpoint") X1)
     (command "change" "l" "" "p" "la" "note-new" "")
     (command "move" "l" "" (getvar "lastpoint") pause)
(princ))

(defun c:EXIT2 ()
     (prompt "now inserting 'double face exit light:' ")
     (setvar "orthomode" 1)
     (f:slay "EL-CLNG-NEW")
     (setq X2 (cond ((> X2 "") X2)(T "")))
  (setq X2a (getstring
      (strcat "\nEnter Fixture number <" X2 "> ? "))
    X2 (cond ((= X2a " ") "")((> X2a "") X2a)(T X2)))
     (prompt "Place fixture, rotate bracket to correct orientation, then move callout to correct location" )
     (command "insert" "exitA" "s" edwgsc "r" 0 pause)
     (command "erase" "l" "")
     (command "insert" "exit2" "s" edwgsc (getvar "lastpoint") pause)
     (command "insert" "exit-mt" "s" edwgsc (getvar "lastpoint") pause)
     (setvar "orthomode" 0)
     (command "insert" "tag1" "s" dwgsc "r" 0 (getvar "viewctr") X2)
     (command "change" "l" "" "p" "la" "note-new" "")
     (command "move" "l" "" (getvar "viewctr") pause)
(princ))

(defun c:EXM ()
     (setvar "orthomode" 1)
     (f:slay "EL-CLNG-NEW")
     (command "insert" "exit-mt" "s" edwgsc "qui,ins" pause pause)
(princ))

(defun c:EXPWR ()
     (layerset  "EP-CIRC-EXST")
(princ))

(defun c:FL ()
     (f:slay "EP-CIRC-NEW")
     (command "insert" "flexcdt" "s" edwgsc "qui,cen" pause pause)
     (f:rlay)
(princ))

(defun c:FLBOX ()
     (prompt "\nNow inserting 'Floor Mounted Box:' ")
     (setvar "orthomode" 1)
     (f:slay "EP-FLOR-NEW")
     (command "insert" "pow41" "s" edwgsc "r" 0 pause)
(f:rlay)
(princ))

(defun c:FLDATA ()
     (prompt "\nNow inserting 'floor mounted data outlet <hollow> :' ")
     (setvar "orthomode" 1)
     (f:slay "SS-FLOR-NEW")
     (command "insert" "pow42a" "s" edwgsc "qui,nea" pause pause)
(f:rlay)
(princ))

(defun c:FLOUT ()
     (prompt "\nNow inserting 'floor mounted duplex receptacle:' ")
     (setvar "orthomode" 1)
     (f:slay "EP-FLOR-NEW")
     (command "insert" "pow43" "s" edwgsc pause pause)
(f:rlay)
(princ))

(defun c:FLQUAD ()
     (prompt "\nNow inserting 'floor mounted quadruplex receptacle:' ")
     (setvar "orthomode" 1)
     (f:slay "EP-FLOR-NEW")
     (command "insert" "pow69" "s" edwgsc pause pause)
(f:rlay)
(princ))

(defun c:FLSIMP ()
     (prompt "\nNow inserting 'floor mounted simplex receptacle:' ")
     (setvar "orthomode" 1)
     (f:slay "EP-FLOR-NEW")
     (command "insert" "pow66" "s" edwgsc pause pause)
(f:rlay)
(princ))

(defun c:FLSPEC ()
     (prompt "\nNow inserting 'floor mounted special purpose receptacle:' ")
     (setvar "orthomode" 1)
     (f:slay "EP-FLOR-NEW")
     (command "insert" "pow79" "s" edwgsc pause pause)
(f:rlay)
(princ))

(defun c:FLTELE ()
     (prompt "\nNow inserting 'floor mounted telephone receptacle <solid filled> :' ")
     (setvar "orthomode" 1)
     (f:slay "SS-FLOR-NEW")
     (command "insert" "pow42" "s" edwgsc pause pause)
(f:rlay)
(princ))

(defun c:FLTD ()
     (prompt "\nNow inserting 'floor mounted combination telephone/data outlet <half solid/half
hollow> :' ")
     (setvar "orthomode" 1)
     (f:slay "SS-FLOR-NEW")
     (command "insert" "pow42b" "s" edwgsc "qui,nea" pause pause)
(f:rlay)
(princ))

(defun c:FUSE ()
(f:slay "EO-DIST-NEW")
(princ "pick entity to insert fuse at end of: ")
(command "insert" "fuse" "s" edwgsc "qui,end" pause pause)
(f:rlay)
(princ))

(defun c:FUSESW ()
(C:EL6)
(princ))

(defun c:GRD ()
     (f:slay "EP-CIRC-NEW")
     (command "insert" "GND" "s" edwgsc "qui,nea" pause pause)
(f:rlay)
(princ))

(defun c:GND ()
(f:slay "EO-DIST-NEW")
(princ "\nPick entity to insert ground symbol at end of: ")
(command "insert" "gnd" "s" edwgsc "qui,end" pause pause)
(f:rlay)
(princ))

(defun c:HM ()
     (setvar "cmdecho" 1)
     (f:slay "EP-CIRC-NEW")
     (setq pt1 (getpoint "first point of arc <arrow end>: "))
     (command "arc" pt1 "e" "qui,nea" pause "d" pause)
     (prompt "arrow rotation angle: ")
     (command "insert" "pow6" "s" edwgsc pt1 pause)
     (c:dt)
     (c:lp)
(f:rlay)
(princ))

; <Home Run: Simple>  -  !!! BETA TEST ONLY !!!
(defun c:HM1 (/ pnt1 cir1 om)
     (setvar "cmdecho" 0)
     (f:slay "EP-CIRC-NEW")
	(setq om (getvar "orthomode"))
     (setvar "orthomode" 0)
     (command "osnap" "nea")
	(setq pnt1 (getpoint "Pick Homerun Start (Non-Arrow End): "))
     (command "osnap" "non")
     (command "arc" pnt1 "e" pause "d" pause)
     (prompt "arrow rotation angle: ")
     (command "insert" "pow6" "s" edwgsc "@" pause)
(f:rlay)
(princ))

; <Home Run: Simple starting at a circle>  -  !!! BETA TEST ONLY !!!
(defun c:HM1C (/ pnt1 cir1 om)
     (setvar "cmdecho" 0)
     (f:slay "EP-CIRC-NEW")
	(setq om (getvar "orthomode"))
     (setvar "orthomode" 0)
     (command "osnap" "qua")
	(setq pnt1 (getpoint "Pick Circle for Homerun Start (Non-Arrow End): "))
     (command "osnap" "non")
     (command "circle" "cen" pnt1 "qua" pnt1)
     (setq cir1 (entlast))
     (command "arc" "cen" pnt1 "e" pause "d" pause)
     (prompt "arrow rotation angle: ")
     (command "insert" "pow6" "s" edwgsc "@" pause)
     (command "trim" "auto" cir1 "" "cen" pnt1 "")
     (command "erase" cir1 "")
     (command "redraw")
(f:rlay)
(princ))

; <Home Run: 5-point Pline Method>  -  !!! BETA TEST ONLY !!!
(defun c:HM2 (/ pnt1 cir1 om)
     (setvar "cmdecho" 0)
     (f:slay "EP-CIRC-NEW")
     (setq om (getvar "orthomode"))
     (setvar "orthomode" 0)
     (command "osnap" "nea")
	(setq pnt1 (getpoint "Pick 5-point Pline Homerun Start Point (Non-Arrow End): "))
     (command "osnap" "non")
	(command "pline" pnt1 pause pause pause pause "") 
	(command "pedit" "l" "s" "")
     (prompt "Align Arrow: ")
     (command "insert" "pow6" "s" edwgsc "@" pause)
     (setvar "orthomode" om)
(f:rlay)
(princ))

; <Home Run: 5-point Pline Method starting at a circle>  -  !!! BETA TEST ONLY !!!
(defun c:HM2C (/ pnt1 cir1 om)
     (setvar "cmdecho" 0)
     (f:slay "EP-CIRC-NEW")
     (setq om (getvar "orthomode"))
     (setvar "orthomode" 0)
     (command "osnap" "qua")
	(setq pnt1 (getpoint "Pick Circle for 5-point Pline Homerun Start (Non-Arrow End): "))
     (command "osnap" "non")
     (command "circle" "cen" pnt1 "qua" pnt1)
     (setq cir1 (entlast))
	(command "pline" "cen" pnt1 pause pause pause pause "") 
	(command "pedit" "l" "s" "")
     (prompt "Align Arrow: ")
     (command "insert" "pow6" "s" edwgsc "@" pause)
     (command "trim" "auto" cir1 "" "cen" pnt1 "")
     (command "erase" cir1 "")
     (command "redraw")
     (setvar "orthomode" om)
(f:rlay)
(princ))

(defun C:IGD ()
     (prompt "\nNow inserting 'iso gnd duplex outlet:' ")
     (setvar "orthomode" 1)
     (f:slay "EP-WALL-NEW")
     (command "insert" "pow35" "s" edwgsc "qui,nea" pause pause)
(f:rlay)
(princ))

(defun C:IGQ ()
     (prompt "\nNow inserting 'iso gnd quad outlet:' ")
     (setvar "orthomode" 1)
     (f:slay "EP-WALL-NEW")
     (command "insert" "pow27" "s" edwgsc "qui,nea" pause pause)
(f:rlay)
(princ))

(defun c:INCAN ()
     (f:slay "EL-CLNG-NEW")
     (command "insert" "incan" "s" edwgsc pause "")
     (f:rlay)
(princ))

(defun c:IQ ()
     (prompt "\nNow inserting 'iso gnd quad receptacle: '")
     (setvar "orthomode" 1)
     (f:slay "EP-WALL-NEW")
     (command "insert" "pow27" "s" edwgsc "qui,nea" pause pause)
(f:rlay)
(princ))

(defun C:J ()
     (prompt "\nNow inserting 'junction box:' ")
     (f:slay "EP-CIRC-NEW")
     (command "insert" "pow36" "s" edwgsc "r" 0 pause)
(f:rlay)
(princ))

(defun c:LTG ()
     (layerset  "EL-CLNG-NEW")
(princ))

(defun c:METER ()
     (f:slay "EO-DIST-NEW")
     (prompt "\nNow inserting 'meter w/ c.t.'s symbol (el4): ")
     (inblk "el4")
(f:rlay)
(princ))

(defun c:MIC ()
(f:slay "SS-WALL-NEW")
     (command "insert" "pow80A" "s" edwgsc "r" 0 pause)
     (command "erase" "l" "")
     (command "insert" "pow80" "s" edwgsc "r" 0 (getvar "lastpoint"))
     (command "insert" "pow52" "s" edwgsc (getvar "lastpoint") pause)
;(command "insert" "pow80" "s" edwgsc "r" 0 pause)
(princ))

(defun c:MPUSH ()
     (prompt "\nNow inserting 'mushroom pushbutton:' ")
     (setvar "orthomode" 1)
     (f:slay "EP-WALL-NEW")
     (command "insert" "pow47a" "s" edwgsc "r" 0 pause)
(f:rlay)
(princ))

(defun c:MST ()
     (prompt "\nNow inserting 'magnetic 2 pole starter:' ")
     (setvar "orthomode" 1)
     (f:slay "EP-WALL-NEW")
     (command "insert" "pow11" "s" edwgsc "r" 0 pause)
(f:rlay)
(princ))

(defun c:MT ()
     (setvar "orthomode" 1)
     (command "insert" "mount" "s" edwgsc pause pause)
(f:rlay)
(princ))

(defun c:MTR ()
     (f:slay "EP-ACLG-NEW")
     (setvar "orthomode" 1)
     (prompt "pick insertion point of motor, starter, disc. symbol: ")
     (command "insert" "motor" "s" edwgsc pause pause)
     (f:rlay)
(princ))

(defun c:MTR1 ()
     (f:slay "EP-ACLG-NEW")
     (setvar "orthomode" 1)
     (prompt "pick insertion point of motor, starter, disc. symbol: ")
     (command "insert" "motor1" "s" edwgsc pause pause)
     (f:rlay)
(princ))

(defun c:NC ()
     (prompt "\nNow inserting 'nurse call station :' ")
     (setvar "orthomode" 1)
     (f:slay "SS-WALL-NEW")
     (command "insert" "pow50" "s" edwgsc "qui,nea" pause pause)
(f:rlay)
(princ))

(defun c:OCC ()
     (prompt "\nNow inserting 'occupancy sensor:' ")
     (f:slay "EP-CLNG-NEW")
     (command "insert" "occup" "s" edwgsc "r" 0 pause)
(f:rlay)
(princ))

(defun c:OPCON ()
(f:slay "EO-DIST-NEW")
(princ "pick entity to insert open connection symbol at end of: ")
(command "insert" "el3a" "s" edwgsc "qui,end" pause pause)
(f:rlay)
(princ))

(defun c:OPCT ()
(f:slay "EO-DIST-NEW")
(princ "pick entity to insert open contact symbol at end of: ")
(command "insert" "opct" "s" edwgsc "r" 0 pause)
(f:rlay)
(princ))

(defun c:OUT ()
     (prompt "\nNow inserting 'duplex receptacle:' ")
     (setvar "orthomode" 1)
     (f:slay "EP-WALL-NEW")
     (command "insert" "pow31" "s" edwgsc "qui,nea" pause pause)
(f:rlay)
(princ))

(defun c:out1 ()
  (insert_symbol_perpendicular "pow31" "duplex receptacle" "ep-wall-new")
  (princ)
)

(defun c:P7 ()
     (f:slay "EP-WALL-NEW")
     (command "insert" "pow7" "s" edwgsc  pause pause)
(f:rlay)
(princ))

(defun c:P8 ()
     (f:slay "EP-WALL-NEW")
     (command "insert" "pow8" "s" edwgsc pause pause)
(f:rlay)
(princ))

(defun c:P9 ()
     (f:slay "EP-WALL-NEW")
     (command "insert" "pow9" "s" edwgsc pause pause)
(f:rlay)
(princ))

(defun c:P10 ()
     (f:slay "EP-WALL-NEW")
     (command "insert" "pow10" "s" edwgsc pause pause)
(f:rlay)
(princ))

(defun c:P12 ()
     (f:slay "EP-ACLG-NEW")
     (command "insert" "pow12" "s" edwgsc pause pause)
(f:rlay)
(princ))

(defun c:P19 ()
     (f:slay "EP-ACLG-NEW")
     (inblk "pow19")
(f:rlay)
(princ))

(defun c:PNL ()
     (f:slay "EP-EQPM-NEW")
     (command "insert" "panel" pause 1 1 pause)
(f:rlay)
(princ))

(defun c:PNLF ()
     (f:slay "EP-EQPM-NEW")
(princ "pick on 'panel' block, this item will insert at insertion point of 'panel'")
(command "insert" "pnlface" "s" 1 "qui,ins" pause pause)
(princ))

(defun c:PS1 ()
(command "pedit" "l" "s" "")
(princ))

(defun c:PUSH ()
     (prompt "\nNow inserting 'pushbutton switch:' ")
     (setvar "orthomode" 1)
     (f:slay "EP-WALL-NEW")
     (command "insert" "pow47" "s" edwgsc "r" 0 pause)
(f:rlay)
(princ))

(defun c:PWR ()
     (layerset  "EP-CIRC-NEW")
(princ))

(defun c:QUAD ()
     (prompt "\nNow inserting 'quadraplex receptacle: '")
     (setvar "orthomode" 1)
     (f:slay "EP-WALL-NEW")
     (command "insert" "pow32" "s" edwgsc "qui,nea" pause pause)
(f:rlay)
(princ))

(defun c:RPNL ()
     (f:slay "EP-EQPM-NEW")
     (command "insert" "rpanel" pause 1 1 pause)
(f:rlay)
(princ))

(defun c:SE ()
     (f:slay "EP-CIRC-NEW")
     (setq ort (getvar "orthomode"))
     (setvar "orthomode" 0)
     (setvar "cmdecho" 1)
     (command "arc" "qui,nea" pause "e" "qui,nea" pause "d" pause)
     (f:rlay)
     (setvar "orthomode" ort)
(princ))

(defun c:SEM ()
     (f:slay "EP-ECKT-NEW")
     (setq ort (getvar "orthomode"))
     (setvar "orthomode" 0)
     (setvar "cmdecho" 1)
     (command "arc" "qui,nea" pause "e" "qui,nea" pause "d" pause)
     (f:rlay)
     (setvar "orthomode" ort)
(princ))

(defun c:SED2 (/ pnt1 pnt2 cir1 cir2 om)
     (f:slay "EP-CIRC-NEW")
     (F:MODS (QUOTE ("orthomode" "osmode")))
     (command "undo" "m")
     (setvar "orthomode" 0)
     (command "osnap" "qua")
     (setq pnt1 (getpoint "\nBeginning arc point: "))
     (setq pnt2 (getpoint "\nEnding arc point: "))
     (command "osnap" "non")
     (command "circle" "cen" pnt1 "qua" pnt1)
     (setq cir1 (entlast))
     (command "circle" "cen" pnt2 "qua" pnt2)
     (setq cir2 (entlast))
     (command "arc" "cen" pnt1 "e" "cen" pnt2 "d" pause)
     (command "trim" "auto" cir1 "" "cen" pnt1 "")
     (command "trim" "auto" cir2 "" "cen" pnt2 "")
     (command "erase" cir1 cir2 "")
     (command "redraw")
(f:modr)
(f:rlay)
(princ))

(defun c:SEQ ()
     (f:slay "EP-CIRC-NEW")
     (setq ort (getvar "orthomode"))
     (setvar "orthomode" 0)
     (setvar "cmdecho" 1)
     (command "arc" "qui,qua" pause "e" "qui,qua" pause "d")
     (f:rlay)
     (setvar "orthomode" ort)
(princ))

(defun c:setgrid ()
	(command "grid" "0.25")
	(command "grid" "m" "4")
	(command "snap" "0.25")
	(princ)
)

(defun c:SG14 ()
	(command "grid" "0.25")
	(command "grid" "m" "4")
	(command "snap" "0.25")
	(princ)
)

(defun c:SG18 ()
	(command "grid" "0.125")
	(command "grid" "m" "8")
	(command "snap" "0.125")
	(princ)
)

(defun c:SG116 ()
	(command "grid" "0.0625")
	(command "grid" "m" "16")
	(command "snap" "0.0625")
	(princ)
)

(defun c:SIMP ()
     (prompt "\nNow inserting 'simplex receptacle:' ")
     (setvar "orthomode" 1)
     (f:slay "EP-WALL-NEW")
     (command "insert" "pow30" "s" edwgsc pause pause)
(f:rlay)
(princ))

(defun C:SLA ()
     (prompt "\nNow inserting 'slash line indicator' ")
     (f:slay "EP-WALL-NEW")
     (command "insert" "slash" "s" edwgsc "r" 0 "qui,cen" pause)
(f:rlay)
(princ))

(defun c:SMK ()
     (prompt "\nNow inserting 'smoke detector:' ")
     (f:slay "FA-CLNG-NEW")
     (command "insert" "pow44" "s" edwgsc pause 0 "")
     (f:rlay)
(princ))

(defun c:SPEC ()
     (layerset  "SS-WALL-NEW")
(princ))

(defun c:SPK ()
     (prompt "\nNow inserting 'speaker :' ")
     (setvar "orthomode" 1)
     (f:slay "SS-CLNG-NEW")
     (command "insert" "pow51" "s" edwgsc "r" 0 pause)
(f:rlay)
(princ))

(defun c:SQJ ()
     (prompt "\nNow inserting 'square junction box:' ")
     (f:slay "EP-FLOR-NEW")
     (command "insert" "pow36a" "s" edwgsc "r" 0 pause)
(f:rlay)
(princ))

(defun c:START ()
     (f:slay "EO-DIST-NEW")
     (prompt "\nNow inserting '(el7) starter symbol': ")
     (inblk "el7")
(f:rlay)
(princ))

(defun c:SW ()
     (f:slay "EP-WALL-NEW")
     (setvar "orthomode" 1)
     (command "insert" "pow15" "s" edwgsc "qui,nea" pause pause)
     (f:rlay)
(princ))

(defun c:SWM ()
     (prompt "\nNow inserting 'micro-switch:' ")
     (setvar "orthomode" 1)
     (f:slay "EP-WALL-NEW")
     (command "insert" "pow37" "s" edwgsc "r" "0" pause)
     (f:rlay)
(princ))

(defun c:SWOUT ()
     (prompt "\nNow inserting 'split wired duplex receptacle:' ")
     (setvar "orthomode" 1)
     (f:slay "EP-WALL-NEW")
     (command "insert" "pow29" "s" edwgsc pause pause)
(f:rlay)
(princ))

(defun c:SWT ()
     (prompt "\nNow inserting 'time switch:' ")
     (setvar "orthomode" 1)
     (f:slay "EP-WALL-NEW")
     (command "insert" "pow13" "s" edwgsc pause pause)
(f:rlay)
(princ))

(defun c:T ()
     (prompt "\nNow inserting 'telephone receptacle <solid filled>:' ")
     (setvar "orthomode" 1)
     (f:slay "SS-WALL-NEW")
     (command "insert" "pow38" "s" edwgsc "qui,nea" pause pause)
(f:rlay)
(princ))

(defun c:T2 ()
     (prompt "\nNow inserting 'telephone receptacle <solid filled>:' ")
     (setvar "orthomode" 1)
     (f:slay "SS-WALL-NEW")
     (command "insert" "pow39" "s" edwgsc "qui,nea" pause pause)
(f:rlay)
(princ))

(defun c:TD ()
     (prompt "\nNow inserting 'combination telephone/data outlet <half solid/half hollow> :' ")
     (setvar "orthomode" 1)
     (f:slay "SS-WALL-NEW")
     (command "insert" "pow63" "s" edwgsc "qui,nea" pause pause)
(f:rlay)
(princ))

(defun c:TRK ()
     (prompt "\nNow inserting track lighting with jbox: ")
     (f:slay "EL-CLNG-NEW")
     (setvar "orthomode" 1)
     (command "insert" "trackltg" "s" edwgsc pause pause)
(f:rlay)
(princ))

(defun c:TROF14 ()
     (prompt "\nNow inserting 1'x4' troffer at intersection: ")
     (f:slay "EL-CLNG-NEW")
     (setvar "orthomode" 1)
     (setq T14 (cond ((> T14 "") T14)(T "")))
  (setq T14a (getstring
      (strcat "\nEnter Fixture number <" T14 "> ? "))
    T14 (cond ((= T14a " ") "")((> T14a "") T14a)(T T14)))
     (prompt "\nPick intersection point to insert to and then rotation")
     (command "insert" "trof14" "s" 1 "qui,int" pause pause)
     (command "insert" "tag1" "s" dwgsc "r" 0 (getvar "lastpoint") T14)
     (command "change" "l" "" "p" "la" "note-new" "")
     (setvar "orthomode" 0)
     (command "move" "l" "" (getvar "lastpoint") pause)
     (c:burst)
(f:rlay)
(princ))

(defun c:TROF14J ()
     (prompt "\nNow inserting 1'x4' troffer with j-box at intersection: ")
     (f:slay "EL-CLNG-NEW")
     (setvar "orthomode" 1)
     (setq T14j (cond ((> T14j "") T14j)(T "")))
  (setq T14ja (getstring
      (strcat "\nEnter Fixture number <" T14j "> ? "))
    T14j (cond ((= T14ja " ") "")((> T14ja "") T14ja)(T T14j)))
     (prompt "\nPick intersection point to insert to and then rotation")
     (command "insert" "trof14j" "s" 1 "qui,int" pause pause)
     (command "insert" "tag1" "s" dwgsc "r" 0 (getvar "lastpoint") T14j)
     (command "change" "l" "" "p" "la" "note-new" "")
     (setvar "orthomode" 0)
     (command "move" "l" "" (getvar "lastpoint") pause)
(f:rlay)
(princ))

(defun c:TROF22 ()
     (prompt "\nNow inserting 2'x2' troffer at intersection: ")
     (f:slay "EL-CLNG-NEW")
     (setvar "orthomode" 1)
     (setq T22 (cond ((> T22 "") T22)(T "")))
  (setq T22a (getstring
      (strcat "\nEnter Fixture number <" T22 "> ? "))
    T22 (cond ((= T22a " ") "")((> T22a "") T22a)(T T22)))
     (prompt "\nPick intersection point to insert to and then rotation")
     (command "insert" "trof22" "s" 1 "qui,int" pause pause)
     (command "insert" "tag1" "s" dwgsc "r" 0 (getvar "lastpoint") T22)
     (command "change" "l" "" "p" "la" "note-new" "")
     (setvar "orthomode" 0)
     (command "move" "l" "" (getvar "lastpoint") pause)
(f:rlay)
(princ))

(defun c:TROF22J ()
     (prompt "\nNow inserting 2'x2' troffer with j-box at intersection: ")
     (f:slay "EL-CLNG-NEW")
     (setvar "orthomode" 1)
     (setq T22j (cond ((> T22j "") T22j)(T "")))
  (setq T22ja (getstring
      (strcat "\nEnter Fixture number <" T22j "> ? "))
    T22j (cond ((= T22ja " ") "")((> T22ja "") T22ja)(T T22j)))
     (prompt "\nPick intersection point to insert to and then rotation")
     (command "insert" "trof22j" "s" 1 "qui,int" pause pause)
     (command "insert" "tag1" "s" dwgsc "r" 0 (getvar "lastpoint") T22j)
     (command "change" "l" "" "p" "la" "note-new" "")
     (setvar "orthomode" 0)
     (command "move" "l" "" (getvar "lastpoint") pause)
(f:rlay)
(princ))

(defun c:TROF24 ()
     (prompt "\nNow inserting 2'x4' troffer at intersection: ")
     (f:slay "EL-CLNG-NEW")
     (setvar "orthomode" 1)
     (setq T24 (cond ((> T24 "") T24)(T "")))
  (setq T24a (getstring
      (strcat "\nEnter Fixture number <" T24 "> ? "))
    T24 (cond ((= T24a " ") "")((> T24a "") T24a)(T T24)))
     (prompt "\nPick intersection point to insert to and then rotation")
     (command "insert" "trof24" "s" 1 "qui,int" pause pause)
     (command "insert" "tag1" "s" dwgsc "r" 0 (getvar "lastpoint") T24)
     (command "change" "l" "" "p" "la" "note-new" "")
     (setvar "orthomode" 0)
     (command "move" "l" "" (getvar "lastpoint") pause)
(f:rlay)
(princ))

(defun c:TROF24J ()
     (prompt "\nNow inserting 2'x4' troffer with j-box at intersection: ")
     (f:slay "EL-CLNG-NEW")
     (setvar "orthomode" 1)
     (setq T24j (cond ((> T24j "") T24j)(T "")))
  (setq T24ja (getstring
      (strcat "\nEnter Fixture number <" T24j "> ? "))
    T24j (cond ((= T24ja " ") "")((> T24ja "") T24ja)(T T24j)))
     (prompt "\nPick intersection point to insert to and then rotation")
     (command "insert" "trof24j" "s" 1 "qui,int" pause pause)
     (command "insert" "tag1" "s" dwgsc "r" 0 (getvar "lastpoint") T24j)
     (command "change" "l" "" "p" "la" "note-new" "")
     (setvar "orthomode" 0)
     (command "move" "l" "" (getvar "lastpoint") pause)
(f:rlay)
(princ))

(defun c:TV ()
     (prompt "\nNow inserting 'TV Cable receptacle:' ")
     (f:slay "SS-WALL-NEW")
     (setvar "orthomode" 1)
     (command "insert" "pow40A" "s" edwgsc "r" 0 pause)
     (command "erase" "l" "")
     (command "insert" "pow40" "s" edwgsc "r" 0 (getvar "lastpoint"))
     (command "insert" "pow52" "s" edwgsc (getvar "lastpoint") pause)
(f:rlay)
(princ))

(defun c:UP ()
     (f:slay "EP-CIRC-NEW")
     (command "insert" "up" "s" edwgsc "qui,end" pause "")
     (f:rlay)
(princ))

(defun c:WL ()
     (prompt "\nNow inserting wall mounted downlight: ")
     (f:slay "EL-WALL-NEW")
     (setvar "orthomode" 1)
     (command "insert" "walllght" "s" edwgsc "qui,nea" pause pause)
(f:rlay)
(princ))

(defun c:WM ()
     (prompt "\nNow inserting 'wiremold raceway:' ")
     (setvar "orthomode" 1)
     (f:slay "EP-WALL-NEW")
     (command "insert" "pow14" "s" edwgsc pause pause)
(f:rlay)
(princ))

(defun c:XFMR (/ pt rat)
(setq rat
     (getstring
          (strcat "\nNormal ( 15, 30, 45, 75, 112.5, 150, 225, 300, 500 ,750, 1000 )
                   \nNon-Linear ( 15N, 30N, 45N, 75N, 112.5N, 150N, 225N, 300N, 500N )
                   \nEnter Transformer KVA Rating from the list abvove: ")
     )
)
     (f:slay "EP-EQPM-NEW")
(setq pt (getpoint "\nPick Insertion Point: "))
(if (= rat "15") (command "pline" pt "@23,0" "@0,17" "@-23,0" "c"))
(if (= rat "15N") (command "pline" pt "@24,0" "@0,18" "@-24,0" "c"))
(if (= rat "30") (command "pline" pt "@24,0" "@0,19" "@-24,0" "c"))
(if (= rat "30N") (command "pline" pt "@28,0" "@0,24" "@-28,0" "c"))
(if (= rat "45") (command "pline" pt "@24,0" "@0,19" "@-24,0" "c"))
(if (= rat "45N") (command "pline" pt "@33,0" "@0,28" "@-33,0" "c"))
(if (= rat "75") (command "pline" pt "@32,0" "@0,24" "@-32,0" "c"))
(if (= rat "75N") (command "pline" pt "@33,0" "@0,36" "@-33,0" "c"))
(if (= rat "112.5") (command "pline" pt "@32,0" "@0,24" "@-32,0" "c"))
(if (= rat "112.5N") (command "pline" pt "@40,0" "@0,30" "@-40,0" "c"))
(if (= rat "150") (command "pline" pt "@36,0" "@0,24" "@-36,0" "c"))
(if (= rat "150N") (command "pline" pt "@45,0" "@0,32" "@-45,0" "c"))
(if (= rat "225") (command "pline" pt "@39,0" "@0,29" "@-39,0" "c"))
(if (= rat "225N") (command "pline" pt "@56,0" "@0,40" "@-56,0" "c"))
(if (= rat "300") (command "pline" pt "@48,0" "@0,31" "@-48,0" "c"))
(if (= rat "300N") (command "pline" pt "@64,0" "@0,42" "@-64,0" "c"))
(if (= rat "500") (command "pline" pt "@48,0" "@0,36" "@-48,0" "c"))
(if (= rat "500N") (command "pline" pt "@60,0" "@0,50" "@-60,0" "c"))
(if (= rat "750") (command "pline" pt "@60,0" "@0,50" "@-60,0" "c"))
(if (= rat "1000") (command "pline" pt "@72,0" "@0,54" "@-72,0" "c"))
(command "rotate" (entlast) "" pt)
(f:rlay)
(princ))

(defun c:XFMR2 ()
(C:EL1)
(princ))

;------------------------------<<  End of File  >>------------------------------

(defun c:14 ()
(c:TROF14) (PRINC))

(defun c:14J ()
(C:TROF14J) (PRINC))

(defun c:22 ()
(C:TROF22) (PRINC))

(defun c:22J ()
(C:TROF22J) (PRINC))

(defun c:24 ()
(C:TROF24) (PRINC))

(defun c:24J ()
(C:TROF24J) (PRINC))

(defun c:F22 ()
(C:EM22) (PRINC))

(defun c:F24 ()
(C:EM24) (PRINC))

(defun c:F14 ()
     (prompt "\nNow inserting 1'x4' emergency indicator: ")
     (f:slay "EL-CLNG-NEW")
     (setvar "orthomode" 1)
     (command "insert" "fill14" "s" 1 "qui,end" pause pause)
(f:rlay)
(princ))

(defun c:GND ()
     (f:slay "EO-DIST-NEW")
     (princ "\nPick entity to insert ground symbol at end of: ")
(command "insert" "gnd" "s" edwgsc "qui,end" pause pause)
(f:rlay)
(princ))


(defun c:EL3 ()
(f:slay "EO-DIST-NEW")
(princ "pick entity to insert el3 (line bolted symbol) at end of: ")
(command "insert" "el3" "s" edwgsc "qui,end" "R" 0 pause)
(f:rlay)
(princ))

(defun c:220 ()
     (prompt "\nNow inserting 'special purpose receptacle:' ")
     (setvar "orthomode" 1)
     (f:slay "EP-WALL-NEW")
     (command "insert" "pow33" "s" edwgsc pause pause)
(f:rlay)
(princ))

;---SCHEDULE FUNCTIONS

(defun C:LSCHD ()
(inschd "SCHD1114")
(princ))

(defun C:LSCHDM ()
(inschd "SCHD1105")
(princ))

(defun C:EQSCHD ()
(inschd "SCHD1106")
(princ))

(defun C:MEQSCHD ()
(inschd "SCHD1112")
(princ))

(defun C:KEQSCHD ()
(inschd "SCHD1103")
(princ))

(defun C:RESCHD1 ()
(inschd "SCHD1110")
(princ))

(defun C:RESCHD2 ()
(inschd "SCHD1111")
(princ))

(defun C:LRESCHD ()
(inschd "SCHD1108")
(princ))

(defun C:CONSCHD ()
(inschd "SCHD1102")
(princ))

(defun C:TRXSCHD ()
(inschd "SCHD1107")
(princ))

;---SITE LIGHTING FUNCTIONS

(defun c:1RH ()
     (prompt "\nNow inserting pole mounted Single Rectangular Head Site Light fixture: ")
     (f:slay "EL-EXTR-NEW")
     (setvar "orthomode" 1)
     (setq rh1 (cond ((> rh1 "") rh1)(T "")))
  (setq rh1a (getstring
      (strcat "\nFixture number <" rh1 "> ? "))
    rh1 (cond ((= rh1a " ") "")((> rh1a "") rh1a)(T rh1)))
     (command "insert" "POW71" "s" edwgsc pause pause)
     (command "insert" "tag1" "s" dwgsc "r" 0 (getvar "lastpoint") RH1)
     (command "change" "l" "" "p" "la" "note-new" "")
     (setvar "orthomode" 0)
     (command "move" "l" "" (getvar "lastpoint") pause)
(f:rlay)
(princ))

(defun c:2RH ()
     (prompt "\nNow inserting pole mounted Double Rectangular Head Site lighting fixture: ")
     (f:slay "EL-EXTR-NEW")
     (setvar "orthomode" 1)
     (setq rh2 (cond ((> rh2 "") rh2)(T "")))
  (setq rh2a (getstring
      (strcat "\nFixture number <" rh2 "> ? "))
    rh2 (cond ((= rh2a " ") "")((> rh2a "") rh2a)(T rh2)))
     (command "insert" "POW72" "s" edwgsc pause pause)
     (command "insert" "tag1" "s" dwgsc "r" 0 (getvar "lastpoint") RH2)
     (command "change" "l" "" "p" "la" "note-new" "")
     (setvar "orthomode" 0)
     (command "move" "l" "" (getvar "lastpoint") pause)
(f:rlay)
(princ))

(defun c:3RH ()
     (prompt "\nNow inserting pole mounted Triple Rectangular Head Site Light fixture: ")
     (f:slay "EL-EXTR-NEW")
     (setvar "orthomode" 1)
     (setq rh3 (cond ((> rh3 "") rh3)(T "")))
  (setq rh3a (getstring
      (strcat "\nFixture number <" rh3 "> ? "))
    rh3 (cond ((= rh3a " ") "")((> rh3a "") rh3a)(T rh3)))
     (command "insert" "POW73" "s" edwgsc pause pause)
     (command "insert" "tag1" "s" dwgsc "r" 0 (getvar "lastpoint") RH3)
     (command "change" "l" "" "p" "la" "note-new" "")
     (setvar "orthomode" 0)
     (command "move" "l" "" (getvar "lastpoint") pause)
(f:rlay)
(princ))

(defun c:4RH ()
     (prompt "\nNow inserting pole mounted Quad Rectangular Head Site Light fixture: ")
     (f:slay "EL-EXTR-NEW")
     (setvar "orthomode" 1)
     (setq rh4 (cond ((> rh4 "") rh4)(T "")))
  (setq rh4a (getstring
      (strcat "\nFixture number <" rh4 "> ? "))
    rh4 (cond ((= rh4a " ") "")((> rh4a "") rh4a)(T rh4)))
     (command "insert" "POW74" "s" edwgsc "r" 0 pause)
     (command "insert" "tag1" "s" dwgsc "r" 0 (getvar "lastpoint") RH4)
     (command "change" "l" "" "p" "la" "note-new" "")
     (setvar "orthomode" 0)
     (command "move" "l" "" (getvar "lastpoint") pause)
(f:rlay)
(princ))

(defun c:1CH ()
     (prompt "\nNow inserting pole mounted Single Circular Head Site Light fixture: ")
     (f:slay "EL-EXTR-NEW")
     (setvar "orthomode" 1)
     (setq ch1 (cond ((> ch1 "") ch1)(T "")))
  (setq ch1a (getstring
      (strcat "\nFixture number <" ch1 "> ? "))
    ch1 (cond ((= ch1a " ") "")((> ch1a "") ch1a)(T ch1)))
     (command "insert" "POW75" "s" edwgsc pause pause)
     (command "insert" "tag1" "s" dwgsc "r" 0 (getvar "lastpoint") CH1)
     (command "change" "l" "" "p" "la" "note-new" "")
     (setvar "orthomode" 0)
     (command "move" "l" "" (getvar "lastpoint") pause)
(f:rlay)
(princ))

(defun c:2cH ()
     (prompt "\nNow inserting pole mounted Double Circular Head Site lighting fixture: ")
     (f:slay "EL-EXTR-NEW")
     (setvar "orthomode" 1)
     (setq ch2 (cond ((> ch2 "") ch2)(T "")))
  (setq ch2a (getstring
      (strcat "\nFixture number <" ch2 "> ? "))
    ch2 (cond ((= ch2a " ") "")((> ch2a "") ch2a)(T ch2)))
     (command "insert" "POW76" "s" edwgsc pause pause)
     (command "insert" "tag1" "s" dwgsc "r" 0 (getvar "lastpoint") CH2)
     (command "change" "l" "" "p" "la" "note-new" "")
     (setvar "orthomode" 0)
     (command "move" "l" "" (getvar "lastpoint") pause)
(f:rlay)
(princ))

(defun c:3CH ()
     (prompt "\nNow inserting pole mounted Triple Circular Head Site Light fixture: ")
     (f:slay "EL-EXTR-NEW")
     (setvar "orthomode" 1)
     (setq ch3 (cond ((> ch3 "") ch3)(T "")))
  (setq ch3a (getstring
      (strcat "\nFixture number <" ch3 "> ? "))
    ch3 (cond ((= ch3a " ") "")((> ch3a "") ch3a)(T ch3)))
     (command "insert" "POW77" "s" edwgsc pause pause)
     (command "insert" "tag1" "s" dwgsc "r" 0 (getvar "lastpoint") CH3)
     (command "change" "l" "" "p" "la" "note-new" "")
     (setvar "orthomode" 0)
     (command "move" "l" "" (getvar "lastpoint") pause)
(f:rlay)
(princ))

(defun c:4CH ()
     (prompt "\nNow inserting pole mounted Quad Circular Head Site Light fixture: ")
     (f:slay "EL-EXTR-NEW")
     (setvar "orthomode" 1)
     (setq ch4 (cond ((> ch4 "") ch4)(T "")))
  (setq ch4a (getstring
      (strcat "\nFixture number <" ch4 "> ? "))
    ch4 (cond ((= ch4a " ") "")((> ch4a "") ch4a)(T ch4)))
     (command "insert" "POW78" "s" edwgsc "r" 0 pause)
     (command "insert" "tag1" "s" dwgsc "r" 0 (getvar "lastpoint") CH4)
     (command "change" "l" "" "p" "la" "note-new" "")
     (setvar "orthomode" 0)
     (command "move" "l" "" (getvar "lastpoint") pause)
(f:rlay)
(princ))

;----------

(defun C:FA ()
     (f:slay "FA-WALL-NEW")
     (setvar "orthomode" 1)
     (prompt "\nPick Insertion Point of 'Fire Alarm Manual Pull Station then rotate bracket:' ")
     (command "insert" "pow45A" "s" edwgsc "r" 0 pause)
     (command "erase" "l" "")
     (command "insert" "pow45" "s" edwgsc "r" 0 (getvar "lastpoint"))
     (command "insert" "pow52" "s" edwgsc (getvar "lastpoint") pause)
     (f:rlay)
(princ))

(defun C:FAD ()
     (prompt "\nPick insertion point of Fire Alarm Duct Detector: ")
     (f:slay "FA-ACLG-NEW")
     (setvar "orthomode" 1)
     (prompt "\nPick insertion point of detector:  ")
     (command "insert" "pow57" "s" edwgsc "r" 0 pause)
     (f:rlay)
(princ))

(defun C:FAH ()
     (f:slay "FA-WALL-NEW")
     (setvar "orthomode" 1)
     (prompt "\nPick Insertion Point of 'Fire Alarm Horn/Strobe Combination:' ")
;     (command "insert" "fastrobepattern-clg" "s" 1 "r" 0 pause)
;     (command "change" "l" "" "p" "la" "eespecsys-pattern" "")
     (command "insert" "pow45a" "s" edwgsc "r" 0 pause)
     (command "erase" "l" "")
     (command "insert" "pow45" "s" edwgsc "r" 0 (getvar "lastpoint"))
     (command "insert" "pow46B" "s" edwgsc (getvar "lastpoint") pause)
     (f:rlay)
(princ))

(defun C:FAH2 ()
     (f:slay "FA-WALL-NEW")
     (setvar "orthomode" 1)
     (prompt "\nPick Insertion Point of 'Fire Alarm Horn only:' ")
;     (command "insert" "fastrobepattern-clg" "s" 1 "r" 0 pause)
;     (command "change" "l" "" "p" "la" "eespecsys-pattern" "")
     (command "insert" "pow45a" "s" edwgsc "r" 0 pause)
     (command "erase" "l" "")
     (command "insert" "pow45" "s" edwgsc "r" 0 (getvar "lastpoint"))
     (command "insert" "pow46a" "s" edwgsc (getvar "lastpoint") pause)
     (f:rlay)
(princ))

(defun c:FAL ()
     (prompt "\nNow inserting 'Fire Alarm station; Strobe only: ")
     (f:slay "FA-WALL-NEW")
     (setvar "orthomode" 1)
     (command "insert" "pow55a" "s" edwgsc "r" 0 pause)
     (command "erase" "l" "")
     (command "insert" "pow55" "s" edwgsc "r" 0 (getvar "lastpoint"))
     (command "insert" "pow52" "s" edwgsc (getvar "lastpoint") pause)
     (f:rlay)
(princ))

(defun c:FAM ()
     (f:slay "FA-WALL-NEW")
     (setvar "orthomode" 1)
     (setvar "osmode" 1088)
     (setq pt1 (getpoint "Pick insertion point of Pull Station: <qui,ins of> "))
     (setvar "osmode" 0)
     (command "insert" "pow52" "s" edwgsc pt1 pause)
     (f:rlay)
(princ))

(defun c:FASD ()
     (prompt "\nNow inserting 'Fire Alarm Smoke Damper: ")
     (f:slay "FA-ACLG-NEW")
     (setvar "orthomode" 1)
     (prompt "\nPick insertion point of Damper:  ")
     (command "insert" "pow56" "s" edwgsc "r" 0 pause)
     (f:rlay)
(princ))

(defun c:FH ()
     (prompt "\nNow inserting 'Heat Detector: '")
     (f:slay "FA-CLNG-NEW")
     (setvar "orthomode" 1)
     (setvar "osmode" 0)
     (command "insert" "pow54" "s" edwgsc "r" 0 PAUSE )
     (f:rlay)
(princ))

(defun c:SD ()
     (prompt "\nNow inserting 'smoke detector: ")
     (f:slay "FA-CLNG-NEW")
     (setvar "orthomode" 1)
     (prompt "\npick insertion point of detector:  ")
     (command "insert" "pow44" "s" edwgsc "r" 0 pause "D")
     (f:rlay)
(princ))

(defun c:SMKP ()
     (prompt "\nNow inserting 'Smoke Detector coverage pattern (below 10' mounting): ' ")
     (f:slay "FA-CLNG-NEW")
     (command "insert" "smk-patt" "s" 1 pause pause)
     (f:rlay)
(princ))


(defun C:PB ()
(COMMAND "PURGE" "B" "" "N") (PRINC))

(defun C:JF ()
     (prompt "\nNow inserting 'junction box with flex conduit:' ")
     (f:slay "EP-CIRC-NEW")
     (command "insert" "pow36" "s" edwgsc "r" 0 pause)
     (command "insert" "flexcdt" "s" edwgsc (getvar "lastpoint") pause)
(f:rlay)
(princ))

(defun C:EA ()
     (f:slay "EP-CIRC-NEW")
(command "arc" "qui,end" pause "e" "qui,end" pause "d")
(f:rlay)
(princ))

(defun C:Q ()
(C:QUAD))


;;;  /------------------------------------------------------------------\
;;;  | The following comprises a new block insertion method.            |
;;;  |                                                                  |
;;;  \------------------------------------------------------------------/

(defun insert_subscript_switch (subscript message /)
  (f:slay "EP-WALL-NEW")
  (f:mods (quote ("attreq" "orthomode")))
  (setvar "attreq" 1)
  (setvar "orthomode" 1)
  (command "insert" "pow15a" "s" edwgsc pause pause subscript)
  (f:rlay)
  (f:modr)
  (princ)
)

(defun c:SW2 ()
  (insert_subscript_switch "2" "\nNow inserting '2-pole switch:' ")
)

(defun c:SW3 ()
  (insert_subscript_switch "3" "\nNow inserting '3-way switch:' ")
)

(defun c:SW4 ()
  (insert_subscript_switch "4" "\nNow inserting '4-way switch:' ")
)

(defun c:SWHP ()
  (insert_subscript_switch "T" "\nNow inserting 'HP rated switch with thermal overloads:' ")
)

(defun c:SWK ()
  (insert_subscript_switch "K" "\nNow inserting 'keyed switch:' ")
)

(defun c:SWL ()
  (insert_subscript_switch "L" "\nNow inserting 'low voltage switch:' ")
)

;;;  /------------------------------------------------------------------\
;;;  | TESTING ZONE                                                     |
;;;  |                                                                  |
;;;  \------------------------------------------------------------------/

(LOAD "LSW_CIRCUIT")
