Attribute VB_Name = "XferLayerSettings"
Option Explicit

Option Base 1

Private Type Layer
    Name As String
    Color As Integer
    LayerOn As Boolean
    Freeze As Boolean
    Plottable As Boolean
End Type

Dim LayerSet() As Layer

Public Sub SetupXrefLayers()

    Dim CurrLayer As AcadLayer
    Dim ActiveDoc As AcadDocument
    Dim InputLine As String
    Dim LayerName As String
    Dim LyrNo As Integer
    
    Set ActiveDoc = ThisDrawing.Application.ActiveDocument
    
    ReDim LayerSet(1)
    
    If FileExists(ActiveDoc.Path & "\" & "Xref_Layers.csv") = True Then
   
        LoadLayersFromFile (ActiveDoc.Path & "\" & "Xref_Layers.csv")
   
    Else
    
        MsgBox "Xref Layer Configuration File Not Found.", vbCritical
        Exit Sub
    
    End If
    
    For Each CurrLayer In ActiveDoc.Layers
    
        If InStr(1, CurrLayer.Name, "|") <> 0 Then 'If it's an xref layer
    
            LayerName = UCase(Mid(CurrLayer.Name, 1 + InStr(1, CurrLayer.Name, "|")))
            
            LayerName = RefineLayerName(LayerName)
            
            If IsDefinedLayer(LayerName) Then
                
                LyrNo = IsDefinedLayer(LayerName)
                
                With CurrLayer
                    .Color = LayerSet(LyrNo).Color
                    .LayerOn = LayerSet(LyrNo).LayerOn
                    .Freeze = LayerSet(LyrNo).Freeze
                    .Plottable = LayerSet(LyrNo).Plottable
                End With

            End If
    
            Call FreezeIfWrongScale(CurrLayer)
    
        End If
    
    Next
    
    ActiveDoc.Regen (acAllViewports)

End Sub

Public Sub SetupSupplimentalXrefLayers()

    Dim CurrLayer As AcadLayer
    Dim ActiveDoc As AcadDocument
    Dim InputLine As String
    Dim LayerName As String
    Dim LyrNo As Integer
    Dim FileToLink
    Dim CurrentFilePath As String
'    Dim MSExcel As Excel.Application
    
    Set ActiveDoc = ThisDrawing.Application.ActiveDocument
    
    ReDim LayerSet(1)
    
    CurrentFilePath = ActiveDoc.Path
    
    CurrentFilePath = CurrentFilePath & "\"
    
    MsgBox CurDir()
    
    If CurrentFilePath <> "" Then
    
        ChDrive Left(CurrentFilePath, 1)
    
        ChDir (CurrentFilePath)
    
    End If
    
    FileToLink = Excel.Application.GetOpenFilename("Layer Settings Files (*.csv), *.csv", , _
                                             "Layer Settings to Implement")
    
    If FileToLink <> False Then
    
        LoadLayersFromFile (FileToLink)
        
        For Each CurrLayer In ActiveDoc.Layers
        
            If InStr(1, CurrLayer.Name, "|") <> 0 Then 'If it's an xref layer
        
                LayerName = UCase(Mid(CurrLayer.Name, 1 + InStr(1, CurrLayer.Name, "|")))
                
                LayerName = RefineLayerName(LayerName)
                
                If IsDefinedLayer(LayerName) Then
                    
                    LyrNo = IsDefinedLayer(LayerName)
                    
                    With CurrLayer
                        .Color = LayerSet(LyrNo).Color
                        .LayerOn = LayerSet(LyrNo).LayerOn
                        .Freeze = LayerSet(LyrNo).Freeze
                        .Plottable = LayerSet(LyrNo).Plottable
                    End With
    
                End If
        
                Call FreezeIfWrongScale(CurrLayer)
        
            End If
        
        Next
        
        ActiveDoc.Regen (acAllViewports)
    
    Else
    
    MsgBox "No layer settings file was selected.", vbExclamation
    
    End If

End Sub


Public Sub ExportXrefLayerSettings()

    Dim ActiveDoc As AcadDocument

    Set ActiveDoc = ThisDrawing.Application.ActiveDocument
    
    ReDim LayerSet(1)
    
    ' 1st... Load Existing Layer Settings (if any)
    
    If FileExists(ActiveDoc.Path & "\" & "Xref_Layers.csv") Then _
        Call LoadLayersFromFile(ActiveDoc.Path & "\" & "Xref_Layers.csv")
    
'    MsgBox "No of Layers: " & UBound(LayerSet) & vbCrLf, _
'       vbInformation, "Previous Settings"
           
    ' 2nd... Add in Settings from the Current Drawing
           
    Call StoreXrefLayerSettings
    
'    MsgBox "No of Layers: " & UBound(LayerSet) & vbCrLf, _
'       vbInformation, "New Settings"
       
    ' 3rd... Output the combined settings to a file
       
    Call WriteSettingsToFile

End Sub

Private Function FileExists(fname) As Boolean
'   Returns TRUE if the file exists
   Dim X As String
   X = Dir(fname)
   If X <> "" Then FileExists = True _
       Else FileExists = False
End Function

Private Function SameSettings(Layer1 As Layer, Layer2 As Layer) As Boolean

    SameSettings = True
    
    If Layer1.Color <> Layer2.Color Then
        SameSettings = False
        Exit Function
    End If
    
    If Layer1.LayerOn <> Layer2.LayerOn Then
        SameSettings = False
        Exit Function
    End If
    
    If Layer1.Freeze <> Layer2.Freeze Then
        SameSettings = False
        Exit Function
    End If
    
    If Layer1.Plottable <> Layer2.Plottable Then
        SameSettings = False
        Exit Function
    End If

End Function

Private Sub AddToLayerSet(NewLayer As Layer)

    Dim LyrNo As Integer
    Dim LayerName As String
    
    LayerName = RefineLayerName(NewLayer.Name)

    If IsDefinedLayer(LayerName) Then
    
        LyrNo = IsDefinedLayer(LayerName)
        
'        If Not SameSettings(NewLayer, LayerSet(LyrNo)) Then
'
'            Select Case MsgBox( _
'                "Overwrite layer setting..." & vbCrLf & _
'                vbCrLf & _
'                "Layer Name:" & vbTab & vbTab & LayerSet(LyrNo).Name & vbCrLf & _
'                "Layer Color:" & vbTab & vbTab & LayerSet(LyrNo).Color & vbCrLf & _
'                "Layer On State:" & vbTab & vbTab & LayerSet(LyrNo).LayerOn & vbCrLf & _
'                "Layer Freeze State:" & vbTab & LayerSet(LyrNo).Freeze & vbCrLf & _
'                "Layer Plottable State:" & vbTab & LayerSet(LyrNo).Plottable & vbCrLf & _
'                vbCrLf & _
'                "...with this?" & vbCrLf & _
'                vbCrLf & _
'                "Layer Name:" & vbTab & vbTab & LayerName & vbCrLf & _
'                "Layer Color:" & vbTab & vbTab & NewLayer.Color & vbCrLf & _
'                "Layer On State:" & vbTab & vbTab & NewLayer.LayerOn & vbCrLf & _
'                "Layer Freeze State:" & vbTab & NewLayer.Freeze & vbCrLf & _
'                "Layer Plottable State:" & vbTab & NewLayer.Plottable, _
'                vbYesNo, _
'                "Overwrite setting?")
'
'            Case vbYes
'
'            Case vbNo
'
'                Exit Sub
'
'            End Select
'
'        End If
    
    Else
    
        If LayerSet(1).Name = "" Then
        
            LyrNo = 1
        
        Else
    
            LyrNo = UBound(LayerSet) + 1
           
            ReDim Preserve LayerSet(LyrNo)
            
        End If
    
    End If
    
    LayerSet(LyrNo).Name = LayerName
    LayerSet(LyrNo).Color = NewLayer.Color
    LayerSet(LyrNo).LayerOn = NewLayer.LayerOn
    LayerSet(LyrNo).Freeze = NewLayer.Freeze
    LayerSet(LyrNo).Plottable = NewLayer.Plottable

End Sub

Private Sub LoadLayersFromFile(FullFileName As String)

    Dim SampleLine As String
    Dim UseFileNo As Integer
    Dim LayerInfo As Variant 'array containing info from file
    Dim LyrNo As Integer
    Dim Counter As Integer
    Dim TempLayer As Layer

    'On Error GoTo FinishUp

    UseFileNo = FreeFile

    LyrNo = 1

    Open FullFileName For Input As #UseFileNo

    Line Input #UseFileNo, SampleLine

    Do While Not EOF(UseFileNo)

        Line Input #UseFileNo, SampleLine

        SampleLine = StripQuotes(SampleLine)

        LayerInfo = Split(SampleLine, ",")

        With TempLayer
            .Name = LayerInfo(0)
            .Color = LayerInfo(1)
            .LayerOn = LayerInfo(2)
            .Freeze = LayerInfo(3)
            .Plottable = LayerInfo(4)
        End With
        
        Call AddToLayerSet(TempLayer)
        
        LyrNo = LyrNo + 1

    Loop

FinishUp:

    Close #UseFileNo

End Sub

Private Function IsTrue(ByVal TestString As String) As Boolean

   If TestString = "TRUE" Then
       IsTrue = True
   Else
       IsTrue = False
   End If
       
End Function

Private Function IsDefinedLayer(LyrName As String) As Variant

    Dim i As Integer
        
    For i = LBound(LayerSet) To UBound(LayerSet)
    
        If LayerSet(i).Name = LyrName Then
            IsDefinedLayer = i
            Exit Function
        End If
    
    Next

    IsDefinedLayer = False

End Function

Private Function StripQuotes(SampleString As String) As String

   Dim StrLen As Integer
   Dim StrPos As Integer
   
   StrLen = Len(SampleString)
   StrPos = 1
   
   Do
       
       If (Mid(SampleString, StrPos, 1) = """") Then
               
           SampleString = Left(SampleString, StrPos - 1) & Mid(SampleString, StrPos + 1)
           
       End If
       
       StrLen = Len(SampleString)
       StrPos = StrPos + 1
   
   Loop While ((StrLen - StrPos) >= 0)
   
   StripQuotes = SampleString

End Function

Private Sub StoreXrefLayerSettings()

   Dim CurrLayer As AcadLayer
   Dim ActiveDoc As AcadDocument
   Dim LayerName As String
   Dim TempLayer As Layer
   
   Set ActiveDoc = ThisDrawing.Application.ActiveDocument
   
   For Each CurrLayer In ActiveDoc.Layers
   
       If InStr(1, CurrLayer.Name, "|") <> 0 Then 'If it's an xref layer
       
            LayerName = UCase(Mid(CurrLayer.Name, 1 + InStr(1, CurrLayer.Name, "|")))
    
            With TempLayer
                .Name = LayerName
                .Color = CurrLayer.Color
                .LayerOn = CurrLayer.LayerOn
                .Freeze = CurrLayer.Freeze
                .Plottable = CurrLayer.Plottable
            End With
           
            Call AddToLayerSet(TempLayer)
           
       End If
       
   Next

End Sub

Private Sub WriteSettingsToFile()
    
    Dim ActiveDoc As AcadDocument
    Dim InputLine As String
    Dim UseFileNo As Integer
    Dim Counter As Integer
    
    On Error GoTo FinishUp
    
    UseFileNo = FreeFile
    
    Set ActiveDoc = ThisDrawing.Application.ActiveDocument
    
    If FileExists(ActiveDoc.Path & "\" & "Xref_Layers.csv") Then
    
        Select Case MsgBox("File Already Exists.  Update?", vbExclamation + vbYesNo)
    
        Case vbNo
    
            Exit Sub
    
        End Select
    
    End If

    Open ActiveDocument.Path & "\" & "Xref_Layers.csv" _
        For Output As #UseFileNo

    Write #UseFileNo, "Layer Name", "Color", "LayerOn", "Freeze", "Plottable"

    For Counter = LBound(LayerSet) To UBound(LayerSet)

        Write #UseFileNo, LayerSet(Counter).Name, _
                          LayerSet(Counter).Color, _
                          UCase(LayerSet(Counter).LayerOn), _
                          UCase(LayerSet(Counter).Freeze), _
                          UCase(LayerSet(Counter).Plottable)

    Next

    Close #UseFileNo
    
    Exit Sub

FinishUp:

    MsgBox "Error Writing File.", vbCritical, "Error"

    Close #UseFileNo

End Sub



Private Sub FreezeIfWrongScale(Lyr As AcadLayer)

   Dim DwgSc As Integer
   Dim LayerName As String

   DwgSc = ActiveDocument.GetVariable("userr3")

   LayerName = Lyr.Name

   If IsNumeric(Right(LayerName, 3)) Or IsNumeric(Right(LayerName, 4)) Then

       If Right(LayerName, 3) <> DwgSc And Right(LayerName, 2) <> DwgSc Then

           With Lyr
               .LayerOn = False
               .Freeze = True
           End With

       End If

   End If

End Sub

Private Function RefineLayerName(LayerName As String) As String

    If IsNumeric(Right(LayerName, 3)) Or _
        IsNumeric(Right(LayerName, 4)) Then
    
        Do While IsNumeric(Right(LayerName, 1))
            LayerName = Left(LayerName, Len(LayerName) - 1)
        Loop
        
        If Right(LayerName, 1) = "-" Then _
            LayerName = Left(LayerName, Len(LayerName) - 1)
    
    End If
    
    RefineLayerName = LayerName

End Function
